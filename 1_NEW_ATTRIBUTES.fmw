FME workspace 1_NEW_ATTRIBUTES.fmw

Parameters:
- SourceDataset_FFS = C:\Users\ai31986\HCP\Examensarbete\Data\Baskarta\3CIM Baskarta Ajour_med extra_attribut.ffs   # Source FME Feature Store (FFS) File(s)
- DestDataset_FFS = $(FME_MF_DIR)OUTPUT\1_BK_ATTRIBUTES_FIXED.ffs   # Destination FME Feature Store (FFS) File
- SourceDataset_FFS_2 = \\ad.stockholm.se\cli-sd\cc2sd003\006284\Projekt\3CIM\3CIM-IMPLEMENTERING\STHLM_Geodata\Baskarta_3CIM_område_FFS\Kungsholmen Baskarta Ajour_med extra_attribut.ffs   # Source FME Feature Store (FFS) File(s)
- DestDataset_FFS_3 = $(FME_MF_DIR)OUTPUT\1_BK_ATTRIBUTES_FIXED_KUNGSHOLMEN.ffs   # Destination FME Feature Store (FFS) File

Readers:
- FFS_1: FFS from $(SourceDataset_FFS)
- FFS_3: FFS from $(SourceDataset_FFS_2) in SWEREF-99-18-00

Writers:
- FFS_2: FFS to $(DestDataset_FFS) in SWEREF-99-18-00
- FFS_4: FFS to $(DestDataset_FFS_3) in SWEREF-99-18-00

Note: Filter för objekt som =! Line & Area
GeometryFilter
    FILTER_MODE = SIMPLE
    FILTER_MULTI = FILTER_TYPES]"Point Line Area"]FME_CONTROLLER_QUERY_FILE]]FME_CONTROLLER_CHOICE]Simple
    Curve -> AttributeFilter
    Area -> AttributeFilter
Note: Filter enligt _grupp
AttributeFilter
    ATTR_NAME = _grupp
    ATTR_VALUES = <Empty>,<Missing>,<Null>,<Unfiltered>,Anläggning,Bygglov_figur,Byggnad,Infra,Natur
    Anläggning -> AttributeFilter4
    Bygglov_figur -> AttributeFilter6
    Byggnad -> AttributeFilter2
    Infra -> AttributeFilter5
    Natur -> AttributeFilter3

Bookmark: Baskarta Kista
Baskarta_Ajour-FFS (reader FFS_1)
    attributes: DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer, DP_DELETED buffer, TIDSPERIOD-UNDERLAG_GEOIDMODELL varchar(40),
      _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100), TRADSORT_NAMN varchar(100),
      TRADTYP_NAMN varchar(100), KRONRADIE real64, STAMDIAM real64, TRADHOJD real64, TRADSORT int32, TRADTYP int32, VET_NAMN int32, SVE_NAMN varchar(50)
    -> GeometryFilter

Bookmark: Baskarta Kungsholmen
Baskarta_Ajour-FFS (reader FFS_3)
    attributes: DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer, DP_DELETED buffer, TIDSPERIOD-UNDERLAG_GEOIDMODELL varchar(40),
      _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100), TRADSORT_NAMN varchar(100),
      TRADTYP_NAMN varchar(100), KRONRADIE real64, STAMDIAM real64, TRADHOJD real64, TRADSORT int32, TRADTYP int32, VET_NAMN int32, SVE_NAMN varchar(50)
    -> GeometryFilter

Bookmark: AttributeFilter enligt DP_OTYPE_NAME
AttributeFilter2
    ATTR_NAME = DP_OTYPE_NAME
    ATTR_VALUES = <Empty>,<Missing>,<Null>,<Unfiltered>,Bostadsbyggnad,Industribyggnad,Ospecificerad byggnad,Samfundsbyggnad,Samhällsfunktionsbyggnad,Servicebyggnad,Verksamhetsbyggnad,Övrig byggnad
    Bostadsbyggnad -> Bostadsbyggnad
    Industribyggnad -> Industribyggnad
    Ospecificerad byggnad -> Ospec._Byggnad
    Samfundsbyggnad -> Samfundsbyggnad
    Samhällsfunktionsbyggnad -> Samhällsfunktionsbyggnad
    Servicebyggnad -> Servicebyggnad
    Verksamhetsbyggnad -> Verksamhetsbyggnad
    Övrig byggnad -> Övrig_byggnad
AttributeFilter3
    ATTR_NAME = DP_OTYPE_NAME
    ATTR_VALUES = <Empty>,<Missing>,<Null>,<Unfiltered>,Sjö,Vattendrag,Vegetation
    Sjö -> Sjö
    Vattendrag -> Vattendrag
    Vegetation -> Vegetation
AttributeFilter4
    ATTR_NAME = DP_OTYPE_NAME
    ATTR_VALUES = <Empty>,<Missing>,<Null>,<Unfiltered>,Byggnadsanläggning,Hamnanläggning,Idrottsanläggning,Markanläggning,Miljöanläggning,Parkanläggning,Teknikanläggning,Trafikanläggning,Övrig anläggning
    Byggnadsanläggning -> Byggnadsanläggning
    Hamnanläggning -> Hamnanläggning
    Idrottsanläggning -> Idrottsanläggning
    Markanläggning -> Markanläggning
    Miljöanläggning -> Miljöanläggning
    Parkanläggning -> Parkanläggning
    Teknikanläggning -> Teknikanläggning
    Trafikanläggning -> Trafikanläggning
    Övrig anläggning -> Övrig_anläggning
AttributeFilter5
    ATTR_NAME = DP_OTYPE_NAME
    ATTR_VALUES = <Empty>,<Missing>,<Null>,<Unfiltered>,Elnät,Spårnät,Vägavgränsning,Vägutbredning
    Elnät -> Elnät
    Spårnät -> Spårnät
    Vägavgränsning -> Vägavgränsning
    Vägutbredning -> Vägutbredning
AttributeFilter6
    ATTR_NAME = DP_OTYPE_NAME
    ATTR_VALUES = <Empty>,<Missing>,<Null>,<Unfiltered>,Byggnadsdel
    Byggnadsdel -> Byggnadsdel

Bookmark: Byggnad
Bostadsbyggnad: AttributeFilter
    ATTR_NAME = DP_SUBTYPE_NAME
    ATTR_VALUES = <Empty>,<Missing>,<Null>,<Unfiltered>,Enbostadshus,Flerbostadshus
    Enbostadshus -> Junction
    Flerbostadshus -> Junction
Samfundsbyggnad: AttributeFilter
    ATTR_NAME = DP_SUBTYPE_NAME
    ATTR_VALUES = <Empty>,<Missing>,<Null>,<Unfiltered>,Ospec. samfundsbyggnad
    Ospec. samfundsbyggnad -> Junction
Industribyggnad: AttributeFilter
    ATTR_NAME = DP_SUBTYPE_NAME
    ATTR_VALUES = <Empty>,<Missing>,<Null>,<Unfiltered>,Industribyggnad,Ospec. industribyggnad
    Industribyggnad -> Junction
    Ospec. industribyggnad -> Junction
Ospec._Byggnad: AttributeFilter
    ATTR_NAME = DP_SUBTYPE_NAME
    ATTR_VALUES = <Empty>,<Missing>,<Null>,<Unfiltered>,Ospec. byggnad Oregistrerad,Ospec. byggnad Registrerad
    Ospec. byggnad Oregistrerad -> Junction
    Ospec. byggnad Registrerad -> Junction
Samhällsfunktionsbyggnad: AttributeFilter
    ATTR_NAME = DP_SUBTYPE_NAME
    ATTR_VALUES = <Empty>,<Missing>,<Null>,<Unfiltered>,Allmän byggnad,Idrottsbyggnad,Vårdbyggnad
    Allmän byggnad -> Junction
    Idrottsbyggnad -> Junction
    Vårdbyggnad -> Junction
Verksamhetsbyggnad: AttributeFilter
    ATTR_NAME = DP_SUBTYPE_NAME
    ATTR_VALUES = <Empty>,<Missing>,<Null>,<Unfiltered>,Handelsbyggnad,Hotellbyggnad,Kontorsbyggnad,Ospec. verksamhetsbyggnad,Parkeringshus
    Handelsbyggnad -> Junction
    Hotellbyggnad -> Junction
    Kontorsbyggnad -> Junction
    Ospec. verksamhetsbyggnad -> Junction
    Parkeringshus -> Övrig_byggnad
Övrig_byggnad: AttributeFilter
    ATTR_NAME = DP_SUBTYPE_NAME
    ATTR_VALUES = <Empty>,<Missing>,<Null>,<Unfiltered>,Ekonomibyggnad,Kolonistuga,Komplementbyggnad
    <EMPTY> -> Junction
    Ekonomibyggnad -> Junction
    Kolonistuga -> Junction
    Komplementbyggnad -> Junction
Servicebyggnad: AttributeFilter
    ATTR_NAME = DP_SUBTYPE_NAME
    ATTR_VALUES = <Empty>,<Missing>,<Null>,<Unfiltered>,Mobilteknikbod,Offentlig toalett,Regnskydd,Transformator
    Mobilteknikbod -> Junction
    Offentlig toalett -> Junction
    Regnskydd -> Junction
    Transformator -> Junction
Junction
    -> Byggnad

Bookmark: AttributeCreator enligt DP_OTYPE_NAME & DP_SUBTYPE_NAME
Byggnad: AttributeCreator
    ATTR_TABLE:
      SET_TO 1_Temaklass (varchar(7)) = Byggnad
      SET_TO 2_Klass (varchar(7)) = @Value(DP_OTYPE_NAME)
      SET_TO 3_Subklass (varchar(1)) = @Value(DP_SUBTYPE_NAME)
    -> Junction_5
Natur: AttributeCreator
    ATTR_TABLE:
      SET_TO 1_Temaklass (varchar(7)) = Natur
      SET_TO 2_Klass (varchar(7)) = @Value(DP_OTYPE_NAME)
      SET_TO 3_Subklass (varchar(1)) = @Value(DP_SUBTYPE_NAME)
    -> Junction_5
Trappa: AttributeCreator
    ATTR_TABLE:
      SET_TO 1_Temaklass (varchar(7)) = Trappa
      SET_TO 2_Klass (varchar(7)) = @Value(DP_OTYPE_NAME)
      SET_TO 3_Subklass (varchar(1)) = @Value(DP_SUBTYPE_NAME)
    -> Junction_5
Anläggning: AttributeCreator
    ATTR_TABLE:
      SET_TO 1_Temaklass (varchar(10)) = Anläggning
      SET_TO 2_Klass (varchar(7)) = @Value(DP_OTYPE_NAME)
      SET_TO 3_Subklass (varchar(1)) = @Value(DP_SUBTYPE_NAME)
    -> Junction_5
Väg: AttributeCreator
    ATTR_TABLE:
      SET_TO 1_Temaklass (varchar(7)) = Väg
      SET_TO 2_Klass (varchar(7)) = @Value(DP_OTYPE_NAME)
      SET_TO 3_Subklass (varchar(1)) = @Value(DP_SUBTYPE_NAME)
    -> Junction_5
Slask: AttributeCreator
    ATTR_TABLE:
      SET_TO 1_Temaklass (varchar(7)) = Natur
      SET_TO 2_Klass (varchar(7)) = @Value(DP_OTYPE_NAME)
      SET_TO 3_Subklass (varchar(1)) = @Value(DP_SUBTYPE_NAME)
      SET_TO 4_Slask (varchar(4)) = True
    -> Junction_5
Junction_5
    -> NewFeatureType (writer FFS_4)
    -> NewFeatureType (writer FFS_2)

Bookmark: Natur
Sjö: AttributeFilter
    ATTR_NAME = DP_SUBTYPE_NAME
    ATTR_VALUES = <Empty>,<Missing>,<Null>,<Unfiltered>,Sjö,Strand
    Sjö -> Junction_2
    Strand -> Junction_2
Vegetation: AttributeFilter
    ATTR_NAME = DP_SUBTYPE_NAME
    ATTR_VALUES = <Empty>,<Missing>,<Null>,<Unfiltered>,Buskage,Plantering
    Buskage -> Junction_2
    Plantering -> Junction_2
Vattendrag: AttributeFilter
    ATTR_NAME = DP_SUBTYPE_NAME
    ATTR_VALUES = <Empty>,<Missing>,<Null>,<Unfiltered>,Bäck,Dike
    Bäck -> Junction_2
    Dike -> Junction_2
Junction_2
    -> Natur

Bookmark: Anläggning
Markanläggning: AttributeFilter
    ATTR_NAME = DP_SUBTYPE_NAME
    ATTR_VALUES = <Empty>,<Missing>,<Null>,<Unfiltered>,Asfaltplan,Bullerskydd,Grusplan,Slänt,Staket,Stenmur,Stödmur
    Asfaltplan -> Junction_4
    Bullerskydd -> Junction_4
    Grusplan -> Junction_4
    Slänt -> Slask
    Staket -> Junction_4
    Stenmur -> Junction_4
    Stödmur -> Junction_4
Byggnadsanläggning: AttributeFilter
    ATTR_NAME = DP_SUBTYPE_NAME
    ATTR_VALUES = <Empty>,<Missing>,<Null>,<Unfiltered>,Altan,Lanternin,Lastkaj,Skärmtak,Trappa
    Altan -> Junction_4
    Lanternin -> Junction_4
    Lastkaj -> Junction_4
    Skärmtak -> Junction_4
    Trappa -> Trappa
Teknikanläggning: AttributeFilter
    ATTR_NAME = DP_SUBTYPE_NAME
    ATTR_VALUES = <Empty>,<Missing>,<Null>,<Unfiltered>,Bassäng,Elskåp,Mobiltelemast
    Bassäng -> Junction_4
    Elskåp -> Junction_4
    Mobiltelemast -> Junction_4
Hamnanläggning: AttributeFilter
    ATTR_NAME = DP_SUBTYPE_NAME
    ATTR_VALUES = <Empty>,<Missing>,<Null>,<Unfiltered>,Brygga
    Brygga -> Junction_4
Idrottsanläggning: AttributeFilter
    ATTR_NAME = DP_SUBTYPE_NAME
    ATTR_VALUES = <Empty>,<Missing>,<Null>,<Unfiltered>,Idrottsplats
    Idrottsplats -> Junction_4
Trafikanläggning: AttributeFilter
    ATTR_NAME = DP_SUBTYPE_NAME
    ATTR_VALUES = <Empty>,<Missing>,<Null>,<Unfiltered>,Bro,Navföljare,Terrängtrappa,Tunnel
    Bro -> Slask
    Navföljare -> Junction_4
    Terrängtrappa -> Trappa
    Tunnel -> Junction_4
Miljöanläggning: AttributeFilter
    ATTR_NAME = DP_SUBTYPE_NAME
    ATTR_VALUES = <Empty>,<Missing>,<Null>,<Unfiltered>,Kompostfack,Återvinningsstation
    <MISSING> -> Övrig_anläggning
    Kompostfack -> Junction_4
    Återvinningsstation -> Junction_4
Övrig_anläggning: AttributeFilter
    ATTR_NAME = DP_SUBTYPE_NAME
    ATTR_VALUES = <Empty>,<Missing>,<Null>,<Unfiltered>,Ospec. anläggning
    Ospec. anläggning -> Junction_4
Parkanläggning: AttributeFilter
    ATTR_NAME = DP_SUBTYPE_NAME
    ATTR_VALUES = <Empty>,<Missing>,<Null>,<Unfiltered>,Parkbänk
    Parkbänk -> Junction_4
Junction_4
    -> Anläggning

Bookmark: Väg
Vägavgränsning: AttributeFilter
    ATTR_NAME = DP_SUBTYPE_NAME
    ATTR_VALUES = <Empty>,<Missing>,<Null>,<Unfiltered>,Infart,Refug
    Infart -> Junction_6
    Refug -> Junction_6
Vägutbredning: AttributeFilter
    ATTR_NAME = DP_SUBTYPE_NAME
    ATTR_VALUES = <Empty>,<Missing>,<Null>,<Unfiltered>,Parkvägsutbredning,Vägutbredning,Vägutbredning i tunnel
    Parkvägsutbredning -> Junction_6
    Vägutbredning -> Junction_6
    Vägutbredning i tunnel -> Slask
Junction_6
    -> Väg

Bookmark: Slask
Spårnät: AttributeFilter
    ATTR_NAME = DP_SUBTYPE_NAME
    ATTR_VALUES = <Empty>,<Missing>,<Null>,<Unfiltered>,Tunnelbanespår
    Tunnelbanespår -> Junction_3
Elnät: AttributeFilter
    ATTR_NAME = DP_SUBTYPE_NAME
    ATTR_VALUES = <Empty>,<Missing>,<Null>,<Unfiltered>,Högspänningsledning
    Högspänningsledning -> Junction_3
Byggnadsdel: AttributeFilter
    ATTR_NAME = DP_SUBTYPE_NAME
    ATTR_VALUES = <Empty>,<Missing>,<Null>,<Unfiltered>,Bygglov,Rivningslov
    Bygglov -> Junction_3
    Rivningslov -> Junction_3
Junction_3
    -> Slask

Bookmark: 1_NEW_ATTRIBUTES_KISTA
NewFeatureType (writer FFS_2)
    attributes: 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer,
      DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32,
      VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4)

Bookmark: 1_NEW_ATTRIBUTES_KUNGSHOLMEN
NewFeatureType (writer FFS_4)
    attributes: 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer,
      DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32,
      VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4)
