FME workspace 3_SKAPA_YTOR.fmw

Parameters:
- SourceDataset_FFS = C:\Users\ai31986\HCP\Examensarbete\FME Projekt workspaces\2_BK_CLEAN\OUTPUT\2_BK_CLEAN.ffs   # Source FME Feature Store (FFS) File(s)
- SourceDataset_FILEGDB = C:\Users\ai31986\HCP\Examensarbete\Data\NVDB\Trafikverket_NVDB_väg-homogeniserade_2024-04-19_JUSTERAD-LAGE.gdb   # File Geodatabase
- SourceDataset_DGNV8 = C:\Users\ai31986\HCP\Examensarbete\Data\Ramar\Urklipp runt Kistaäng.dgn   # Source Bentley MicroStation Design File(s)
- SourceDataset_FFS_3 = C:\Users\ai31986\HCP\Examensarbete\Data\Baskarta\3CIM Baskarta Ajour_med extra_attribut.ffs   # Source FME Feature Store (FFS) File(s)
- DestDataset_FFS = $(FME_MF_DIR)OUTPUT\3_SKAPA_TRANSPORTYTOR.ffs   # Destination FME Feature Store (FFS) File
- SourceDataset_FFS_13 = C:\Users\ai31986\HCP\Examensarbete\Data\Ramar\VERIF.ffs   # Source FME Feature Store (FFS) File(s)
- SourceDataset_FFS_6 = C:\Users\ai31986\HCP\Examensarbete\FME Projekt workspaces\2_BK_CLEAN\OUTPUT\VERIF_2_BK_CLEAN.ffs   # Source FME Feature Store (FFS) File(s)
- DestDataset_FFS_2 = $(FME_MF_DIR)OUTPUT\VERIF_3_SKAPA_TRANSPORTYTOR.ffs   # Destination FME Feature Store (FFS) File
- SourceDataset_FFS_11 = \\ad.stockholm.se\cli-sd\cc2sd003\006284\Projekt\3CIM\3CIM-IMPLEMENTERING\STHLM_Geodata\Baskarta_3CIM_område_FFS\Kungsholmen Baskarta Ajour_med extra_attribut.ffs   # Source FME Feature Store (FFS) File(s)
- SourceDataset_FFS_10 = C:\Users\ai31986\HCP\Examensarbete\Data\Ramar\RAM_KUNGSHOLMEN.ffs   # Source FME Feature Store (FFS) File(s)
- SourceDataset_FFS_12 = C:\Users\ai31986\HCP\Examensarbete\FME Projekt workspaces\2_BK_CLEAN\OUTPUT\2_BK_CLEAN_KUNGSHOLMEN.ffs   # Source FME Feature Store (FFS) File(s)
- DestDataset_FFS_4 = $(FME_MF_DIR)OUTPUT\3_SKAPA_TRANSPORTYTOR_KUNGSHOLMEN.ffs   # Destination FME Feature Store (FFS) File
- DestDataset_OGCGEOPACKAGE = steg3   # GeoPackage File

Readers:
- FFS_1: FFS from $(SourceDataset_FFS)
- FILEGDB_1: FILEGDB from $(SourceDataset_FILEGDB) in SWEREF-99-TM
- DGNV8_1: DGNV8 from $(SourceDataset_DGNV8) in SWEREF-99-18-00
- FFS_2: FFS from $(SourceDataset_FFS_3) in SWEREF-99-18-00
- FFS_4: FFS from $(SourceDataset_FFS_13) in SWEREF-99-18-00
- FFS_5: FFS from $(SourceDataset_FFS_6) in SWEREF-99-18-00
- FFS_7: FFS from $(SourceDataset_FFS_11) in SWEREF-99-18-00
- FFS_8: FFS from $(SourceDataset_FFS_10) in SWEREF-99-18-00
- FFS_9: FFS from $(SourceDataset_FFS_12) in SWEREF-99-18-00

Writers:
- FFS_3: FFS to $(DestDataset_FFS) in SWEREF-99-18-00
- FFS_6: FFS to $(DestDataset_FFS_2) in SWEREF-99-18-00
- FFS_10: FFS to $(DestDataset_FFS_4) in SWEREF-99-18-00
- OGCGEOPACKAGE_1: OGCGEOPACKAGE to $(DestDataset_OGCGEOPACKAGE) in SWEREF-99-18-00

LineCombiner
    ACCUM_ATTRS_NAME = Use Attributes From One Feature
    CLOSE = yes
    CONNECT_Z_MODE_LOOKUP = FIRST_WINS
    CONSIDER_NODE_ELEVATION_LOOKUP = NO
    DEAGGREGATE_GEOMETRY = Deaggregate
    JUNCTIONS_IGNORE_ATTRIBUTES = No
    LINES_AS_SEGMENTS = No
    NODED = END_NODED
    PRESERVE = no
    BREAK = no
    CONNECT_Z_MODE = First Wins
    CONSIDER_NODE_ELEVATION = no
    TOPOLOGY = End Noded
    LINE -> Tester_9
Note: LineOnAreaOverlayer_3 : Line
Junction_10
    -> Junction_11
Note: BK clean
Junction_11
    -> LineOnAreaOverlayer_3 [LINE]
    -> LineOnAreaOverlayer [LINE]
    -> LineOnAreaOverlayer_7 [LINE]
    -> LineOnAreaOverlayer_5 [LINE]
Note: Filtrera bort attribut
AttributeRemover
    REMOVE_ATTRS = _clipped,_length1,_overlaps,Avvik_540,B_ATK_Matplats,B_Avser_28,B_Beskr_454,B_Cirkulationsplats,B_ForbjudenFardriktning,B_ForbudTrafik,B_Hogst_24,B_Hogst_225,B_Korfa_517,Barig_64,Barig_504,Bredd_156,Brunn___Slamsugning,C_Rekbilvagcykeltrafik,DP_SUBTYPE_NAME,drift_2,entre_380,Europ_16,F_ATK_Matplats,F_Avser_28,F_Beskr_454,F_Cirkulationsplats,F_ForbjudenFardriktning,F_ForbudTrafik,F_Hogst_24,F_Hogst_225,F_Korfa_517,Forva_9,FPV_k_309,Framk_161,FROM_MEASURE,Funktionellt_priovagnat,GCM_belyst,GCM_passage,Hallplats,Hinde_72,Hogst_36,Hogst_46,Hogst_55_30,Huvud_13_1,Ident_191,Kateg_380,Klass_181,Kommu_141,Konst_190,korfa_52,Korfa_524,L_Gagata,L_Gangfartsomrade,L_Mater_301,L_P_ficka,L_Separ_500,L_VVIS,LageF_83,Langd_192,Lanst_15,M_P_ficka,mittr_10,Motortrafikled,Motorvag,Namn_130,Namn_132,Namn_193,Namns_133,OBJECTID,Passa_85,Passe_73,Plank_92,Provisorisk_vag,R_Gagata,R_Gangfartsomrade,R_Mater_301,R_P_ficka,R_Separ_500,R_VVIS,SHAPE_Length,slitl_25,Slitl_152,TattbebyggtOmrade,Tillg_169,TO_MEASURE,Trafi_86,Typ_369,Typ_a_55_29,TypAv_82,Under_14,Under_397,Vagha_6,Vagha_7,Vagkl_564,Vagnummer_ROLE,vagty_41
    -> AttributeFilter
Junction_3
    -> Snipper_3
Junction_2
    -> Snipper_4
AttributeFilter_2
    ATTR_NAME = Vagtr_474
    ATTR_VALUES = <Empty>,<Missing>,<Null>,<Unfiltered>,bilnät,cykelnät,Gång- och cykelnät,gångnät,Infart
    bilnät -> FeatureColorSetter
    cykelnät -> FeatureColorSetter_2
    Gång- och cykelnät -> FeatureColorSetter_4
    gångnät -> FeatureColorSetter_3
    Infart -> FeatureColorSetter_5
Junction
    -> AreaCalculator
Junction_5
    -> PointOnAreaOverlayer [AREA]
Note: Ta bort oönskade attribut
AttributeRemover_2
    REMOVE_ATTRS = _area,_bbox,_clipped,_Compactness,_length,_overlaps,_predicate,_remnant,fme_color,fme_fill_color
    -> NewFeatureType (writer FFS_6)
    -> NewFeatureType (writer FFS_10)
    -> NewFeatureType (writer FFS_3)
    -> Table1 (writer OGCGEOPACKAGE_1)
Table1 (writer OGCGEOPACKAGE_1)
    attributes: Vagtr_474 text(10), LOD2 text(6), ROUTE_ID text(38), Typ_512 text(23), GCM_t_502 text(37), Skymd text(2), 1_Temaklass text(7), 2_Klass text(7), 3_Subklass text(1), DP_OTYPE text, DP_OTYPE_NAME text, DP_CTYPE text, SYMBOL text, DP_OID int, PRODUCT_NAME text, DP_MOD text, CTYPE_NAME text, PROD_ELEV text, PROD_PLANE text, tidpunktForLagesbestamning text, tidpunktForKontrollAvGeometri text, metodIPlanTidsperiodFran datetime, metodIPlanTidsperiodTill datetime, MATANVISNINGAR text(200), STADIUM text(40), absolutLagesosakerhetPlan text(40), metodIPlanTyp text(80), absolutLagesosakerhetHojd text(40), metodIHojdTyp text(80), DP_SIGN text,
      FILL_COLOR text(200), CTABLE text, DP_SUBTYPE text, PROD_CLASS_ID text, _whereBaggis text, DP_OCCURRENCE text, DP_DELETED text, TIDSPERIOD-UNDERLAG_GEOIDMODELL text(40), _grupp text, MARK_TEXT text(40), KANTSTOD_TEXT text(100), KANTSTOD mediumint, MARK mediumint, _matched_records int, INM_LAGE_TEXT text(100), _bygglov_diarienummer_public text(200), DIARIENR mediumint, INMATNINGSANV mediumint, CA_NAME text(80), KOM_ID text(200), HUSNR text(200), UUID_BYGGNAD text(200), _related_suppliers int, INM_LAGE mediumint, LANDMARKE mediumint, VARIANT_NAMN text(100), OSKARP_TEXT text(100), VANSTER_TEXT text(100), KONSTRUERAD_TEXT text(100), ANL_NAMN text(40),
      BREDD float, KONSTRUERAD mediumint, OSKARP mediumint, RELATIV_HOJD float, VARIANT mediumint, VANSTER mediumint, VET_NAMN_NAMN text(100), TRADSORT_NAMN text(100), TRADTYP_NAMN text(100), KRONRADIE double, STAMDIAM double, TRADHOJD double, TRADSORT mediumint, TRADTYP mediumint, VET_NAMN mediumint, SVE_NAMN text(50), 4_Slask text(4), _node_number int, _element_count text(20), _distance double, _closest_candidate_x double, _closest_candidate_y double, _closest_base_x double, _closest_base_y double, _edge_id int, _right_face int, _left_face int, _faces int, _creation_instance text(20), Added_line text(4)

Bookmark: NVDB-Länkar
TNE_FT_VAGDATA (reader FILEGDB_1)
    attributes: ROUTE_ID text(38), FROM_MEASURE double, TO_MEASURE double, Korfa_524 int, F_ATK_Matplats smallint, B_ATK_Matplats smallint, F_Avser_28 text(3), B_Avser_28 text(3), F_Hogst_24 double, B_Hogst_24 double, Hogst_36 double, Hogst_46 double, Hogst_55_30 double, Typ_a_55_29 text(16), Ident_191 text(3000), Konst_190 text(23), Langd_192 double, Namn_193 text(3000), Brunn___Slamsugning smallint, L_Mater_301 text(15), R_Mater_301 text(15), Barig_64 text(25), Barig_504 text(25), C_Rekbilvagcykeltrafik smallint, F_Cirkulationsplats smallint, B_Cirkulationsplats smallint, entre_380 text(36), drift_2 text(34), LageF_83 text(42), TypAv_82 text(59),
      Framk_161 text(47), Klass_181 text(1), FPV_k_309 text(39), Funktionellt_priovagnat smallint, F_ForbjudenFardriktning smallint, B_ForbjudenFardriktning smallint, F_ForbudTrafik smallint, B_ForbudTrafik smallint, F_Beskr_454 text(3000), B_Beskr_454 text(3000), Namn_130 text(3000), Typ_512 text(23), GCM_belyst smallint, GCM_passage smallint, Passa_85 text(93), Trafi_86 text(22), L_Separ_500 text(13), R_Separ_500 text(13), GCM_t_502 text(37), L_Gagata smallint, R_Gagata smallint, L_Gangfartsomrade smallint, R_Gangfartsomrade smallint, F_Hogst_225 text(10), B_Hogst_225 text(10), Hallplats smallint, Plank_92 text(3000), F_Korfa_517 text(9), B_Korfa_517 text(9), mittr_10 text(8),
      Motortrafikled smallint, Motorvag smallint, Provisorisk_vag smallint, L_P_ficka smallint, R_P_ficka smallint, M_P_ficka smallint, Slitl_152 text(6), TattbebyggtOmrade smallint, Tillg_169 text(1), Under_397 text(48), L_VVIS smallint, R_VVIS smallint, slitl_25 text(15), Bredd_156 double, Hinde_72 text(39), Passe_73 double, Vagha_7 text(3000), Vagha_6 text(8), Forva_9 text(22), Avvik_540 text(8), Kateg_380 text(17), Europ_16 smallint, Huvud_13_1 int, Lanst_15 int, Under_14 int, Vagtr_474 text(10), korfa_52 text(17), vagty_41 text(24), Typ_369 text(23), Namn_132 text(3000),
      Namns_133 text(8), Kommu_141 text(3000), Vagkl_564 text(1), Vagnummer_ROLE text(11), OBJECTID objectid, SHAPE_Length double
    -> Reprojector

Bookmark: Förarebete NVDB-länkar
Note: Ändra koordinatsystem
Reprojector
    DEST = SWEREF-99-18-00
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> TV-Clipper [CANDIDATE]
Note: Klipp området med ramen
TV-Clipper: Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Tester_4
Note: Tester_4 [Tester] / Test Clauses: Left ValueOperatorRight Value@Value(Konst_190)=överfartAdvanced: / Preserve Feature Order: Per Output Port
Tester_4
    BOOL_OP = OR
    TEST_CLAUSE = TEST @Value(Konst_190) = överfart
    TEST_MODE = TEST
    PASSED -> Clipper_5 [CANDIDATE]
    FAILED -> Tester_6

Bookmark: Ram Träningsområde Kista
Default (reader DGNV8_1)
    -> TV-Clipper [CLIPPER]
    -> Clipper_4 [CLIPPER]

Bookmark: Ram Testområde Kista
VERIF (reader FFS_4) [off]
    attributes: _creation_instance uint64
    -> TV-Clipper [CLIPPER]
    -> Clipper_4 [CLIPPER]

Bookmark: Ram Testområde Kungsholmen
NewFeatureType (reader FFS_8) [off]
    attributes: _creation_instance uint64
    -> TV-Clipper [CLIPPER]
    -> Clipper_4 [CLIPPER]

Bookmark: BK Kista
Baskarta_Ajour-FFS (reader FFS_2)
    attributes: DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer, DP_DELETED buffer, TIDSPERIOD-UNDERLAG_GEOIDMODELL varchar(40),
      _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100), TRADSORT_NAMN varchar(100),
      TRADTYP_NAMN varchar(100), KRONRADIE real64, STAMDIAM real64, TRADHOJD real64, TRADSORT int32, TRADTYP int32, VET_NAMN int32, SVE_NAMN varchar(50)
    -> Clipper_4 [CANDIDATE]

Bookmark: BK Kungsholmen
Baskarta_Ajour-FFS (reader FFS_7) [off]
    attributes: DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer, DP_DELETED buffer, TIDSPERIOD-UNDERLAG_GEOIDMODELL varchar(40),
      _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100), TRADSORT_NAMN varchar(100),
      TRADTYP_NAMN varchar(100), KRONRADIE real64, STAMDIAM real64, TRADHOJD real64, TRADSORT int32, TRADTYP int32, VET_NAMN int32, SVE_NAMN varchar(50)
    -> Clipper_4 [CANDIDATE]

Bookmark: Trimma bort bro-linjeobjekt ur NVDB-länkarna
Note: Klippa baskartan med ramen
Clipper_4
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Tester_3
Note: Tester för broar
Tester_3
    BOOL_OP = OR
    TEST_CLAUSE = TEST @Value(DP_SUBTYPE_NAME) = Bro
    TEST_MODE = TEST
    PASSED -> GeometryCoercer
Note: Säkerställ fme_line
GeometryCoercer
    GQUERY:
      for $geom in //geometry
      where $geom/count(parent::geometry) = 0
      return number($geom/@fme_id)
    KIND = fme_line
    COERCED -> SmartCleaner_2013
Note: Städa linjerna så ytor kan bildas
SmartCleaner_2013
    LEN = 1
    VAL = 1
    CLEANED -> AreaBuilder
Note: Skapa ytor för klippning av NVDB-länkar
AreaBuilder
    ALLOW_CYCLES = No
    CHECK_CURVE_DIRECTION = No
    CONNECT_Z_MODE_LOOKUP = FIRST_WINS
    CONSIDER_NODE_ELEVATION_LOOKUP = NO
    DEAGGREGATE_INPUT = Deaggregate
    DONUT_CREATION = Yes
    DROP_HOLES = No
    LINES_AS_SEGMENTS = No
    POLY_ACCUM_ATTRS_NAME = Use Attributes From One Feature
    SNAPTYPE = NONE
    CONNECT_Z_MODE = First Wins
    CONSIDER_NODE_ELEVATION = no
    SNAPTYPE_PARAM = None
    AREA -> Clipper_5 [CLIPPER]
Note: Klipp broytorna mot NVDB-linjerna
Clipper_5
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Tester_6

Bookmark: Snippa konstig NVDB linje
Note: Filter för specifikt ID
Tester_6
    BOOL_OP = OR
    TEST_CLAUSE = TEST @Value(OBJECTID) = 126920
    TEST_MODE = TEST
    PASSED -> Snipper
    FAILED -> Tester_36
    FAILED -> Junction_7
Note: Klippning av specifik linje
Snipper
    DEAGGREGATE_INPUT = YES
    ENDLOCATIONATTR = 45
    MEASUREMENTTYPE = 2D
    SNIP_MODE = DISTANCE
    STARTLOCATIONATTR = 0
    SNIPMODE = Distance (Value)
    -> Tester_36
    -> Junction_7
Note: Snipper_6 : Input
Junction_7
    -> Junction_8

Bookmark: Klippning av parkeringsområdesvägar
Note: Tester_36 [Tester] / Test Clauses: LogicLeft ValueOperatorRight Value@Value(Typ_512)=ParkeringsområdesvägOR@Value(Typ_512)=Infartsväg/UtfartsvägOR@Value(Typ_512)=KvartersvägAdvanced: / Preserve Feature Order: Per Output Port
Tester_36
    BOOL_OP = OR
    TEST_CLAUSE:
      TEST @Value(Typ_512) = Parkeringsområdesväg
      TEST @Value(Typ_512) = Infartsväg/Utfartsväg
      TEST @Value(Typ_512) = Kvartersväg
    TEST_MODE = TEST
    PASSED -> LineOnLineOverlayer [LINE]
    FAILED -> LineCombiner
Note: Säkerställ fme_line
GeometryCoercer_8
    GQUERY:
      for $geom in //geometry
      where $geom/count(parent::geometry) = 0
      return number($geom/@fme_id)
    KIND = fme_line
    COERCED -> LineOnLineOverlayer [LINE]
Note: Overlayer av NVDB-länkar och BK
LineOnLineOverlayer
    ATTRS_ACCUM_MODE = Use Attributes From One Feature
    CLEANING_TOLERANCE_LOOKUP = AUTO
    DEAGGREGATE_INPUT = Yes
    GENERATE_LIST_DROP = NO
    OV_ATTR = _overlaps
    SEPARATE_COLLINEAR_SEGMENTS = No
    CLEANING_TOLERANCE = Automatic
    LINE -> Tester_8
Note: Tester_8 [Tester] / Test Clauses: LogicLeft ValueOperatorRight Value@Value(Typ_512)=ParkeringsområdesvägOR@Value(Typ_512)=Infartsväg/UtfartsvägOR@Value(Typ_512)=KvartersvägAdvanced: / Preserve Feature Order: Per Output Port
Tester_8
    BOOL_OP = OR
    TEST_CLAUSE:
      TEST @Value(Typ_512) = Parkeringsområdesväg
      TEST @Value(Typ_512) = Infartsväg/Utfartsväg
      TEST @Value(Typ_512) = Kvartersväg
    TEST_MODE = TEST
    PASSED -> LengthCalculator_2
Note: Beräkna längden för linjeobjekten
LengthCalculator_2
    DIM = 2
    LEN_ATTR = _length1
    MULT = 1
    -> Tester_38
Note: Om kortare än längden 7m --> ta bort
Tester_38
    BOOL_OP = OR
    TEST_CLAUSE = TEST @Value(_length1) < 7
    TEST_MODE = TEST
    FAILED -> LineCombiner

Bookmark: Ta bort ytor med för få NVDB punkter i sig
Note: TV-Clipper : Inside
Junction_8
    -> Snipper_6
Note: Korta ner NVDB-länkarna
Snipper_6
    DEAGGREGATE_INPUT = YES
    ENDLOCATIONATTR = @Evaluate(@Length()-1)
    MEASUREMENTTYPE = 2D
    SNIP_MODE = DISTANCE
    STARTLOCATIONATTR = 1
    SNIPMODE = Distance (Value)
    -> Densifier_5
Note: Öka antalet vertices
Densifier_5
    INTERVAL = 1
    MODE_LOOKUP = xy_uniform
    MODE = Uniform Interval
    DENSIFIED -> Chopper_5
Note: Dela upp länkarna i punkter, enligt vertices
Chopper_5
    DEAGGREGATE_INPUT = Deaggregate
    MAX_VERTICES = 1
    MODE_LOOKUP = VERTEX
    REMNANT_ATTR = _remnant
    MODE = By Vertex
    CHOPPED -> PointOnAreaOverlayer [POINT]
Note: Overlayer med ytorna
PointOnAreaOverlayer
    DEAGGREGATE_INPUT = Yes
    OV_ATTR = _overlaps
    POLYS_FIRST = NO
    AREA -> Tester_5
Note: Tester för _overlaps
Tester_5
    BOOL_OP = OR
    TEST_CLAUSE = TEST @Value(_overlaps) < 7
    TEST_MODE = TEST
    PASSED -> AreaCalculator_3
    FAILED -> Junction_9
Note: Beräkna area för ytorna
AreaCalculator_3
    AREA_ATTR = _area
    AREA_TYPE = Plane Area
    MULT = 1
    -> Tester_7
Note: Filter enligt area
Tester_7
    BOOL_OP = OR
    TEST_CLAUSE = TEST @Value(_area) < 200
    TEST_MODE = TEST
    PASSED -> Junction_9
Junction_9
    -> AttributeRemover_2

Bookmark: 2_BK_CLEAN_TRÄNINGSOMRÅDE_KISTA
NewFeatureType (reader FFS_1)
    attributes: DP_SUBTYPE_NAME buffer
    -> GeometryCoercer_8
    -> Tester_12
    -> Junction_10

Bookmark: 2_BK_CLEAN_TESTOMRÅDE_KISTA
NewFeatureType (reader FFS_5) [off]
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> Junction_10
    -> GeometryCoercer_8
    -> Tester_12

Bookmark: 2_BK_CLEAN_TRÄNINGSOMRÅDE_KUNGSHOLMEN
NewFeatureType (reader FFS_9) [off]
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> Junction_10
    -> GeometryCoercer_8
    -> Tester_12

Bookmark: Klippning av huvudgata och lokalgata S/L
Note: Tester_9 [Tester] / Test Clauses: LogicLeft ValueOperatorRight Value@Value(Typ_512)=HuvudgataOR@Value(Typ_512)=Lokalgata litenOR@Value(Typ_512)=Lokalgata storAdvanced: / Preserve Feature Order: Per Output Port
Tester_9
    BOOL_OP = OR
    TEST_CLAUSE:
      TEST @Value(Typ_512) = Huvudgata
      TEST @Value(Typ_512) = Lokalgata liten
      TEST @Value(Typ_512) = Lokalgata stor
    TEST_MODE = TEST
    PASSED -> LineOnLineOverlayer_2 [LINE]
    FAILED -> AttributeRemover
Note: Test för refug
Tester_12
    BOOL_OP = OR
    TEST_CLAUSE = TEST @Value(DP_SUBTYPE_NAME) = Refug
    TEST_MODE = TEST
    FAILED -> GeometryCoercer_2
Note: Säkerställ fme_line
GeometryCoercer_2
    GQUERY:
      for $geom in //geometry
      where $geom/count(parent::geometry) = 0
      return number($geom/@fme_id)
    KIND = fme_line
    COERCED -> LineOnLineOverlayer_2 [LINE]
Note: Overlayer av NVDB-länkar och BK
LineOnLineOverlayer_2
    ATTRS_ACCUM_MODE = Use Attributes From One Feature
    CLEANING_TOLERANCE_LOOKUP = AUTO
    DEAGGREGATE_INPUT = Yes
    GENERATE_LIST_DROP = NO
    OV_ATTR = _overlaps
    SEPARATE_COLLINEAR_SEGMENTS = No
    CLEANING_TOLERANCE = Automatic
    LINE -> Tester_11
Note: Tester_11 [Tester] / Test Clauses: LogicLeft ValueOperatorRight Value@Value(Typ_512)=HuvudgataOR@Value(Typ_512)=Lokalgata litenOR@Value(Typ_512)=Lokalgata storAdvanced: / Preserve Feature Order: Per Output Port
Tester_11
    BOOL_OP = OR
    TEST_CLAUSE:
      TEST @Value(Typ_512) = Huvudgata
      TEST @Value(Typ_512) = Lokalgata liten
      TEST @Value(Typ_512) = Lokalgata stor
    TEST_MODE = TEST
    PASSED -> LengthCalculator_3
Note: Beräkna längen för linjeobjekten
LengthCalculator_3
    DIM = 2
    LEN_ATTR = _length1
    MULT = 1
    -> Tester_10
Note: Om kortare än längden 7m --> ta bort
Tester_10
    BOOL_OP = OR
    TEST_CLAUSE = TEST @Value(_length1) < 7
    TEST_MODE = TEST
    FAILED -> AttributeRemover

Bookmark: Filtrering
Note: Filter på Vag 474
AttributeFilter
    ATTR_NAME = Vagtr_474
    ATTR_VALUES = <Empty>,<Missing>,<Null>,<Unfiltered>,bilnät,cykelnät,gångnät
    bilnät -> AttributeFilter_3
    cykelnät -> AttributeCreator_4
    gångnät -> AttributeCreator_5
Note: Filter på Typ_512
AttributeFilter_3
    ATTR_NAME = Typ_512
    ATTR_VALUES = <Empty>,<Missing>,<Null>,<Unfiltered>,Huvudgata,Infartsväg/Utfartsväg,Kvartersväg,Lokalgata liten,Lokalgata stor,Parkeringsområdesväg
    Huvudgata -> Junction_4
    Infartsväg/Utfartsväg -> Junction_6
    Kvartersväg -> Junction_6
    Lokalgata liten -> Junction_4
    Lokalgata stor -> Junction_4
    Parkeringsområdesväg -> Junction_6
Junction_4
    -> Snipper_2
Junction_6
    -> Snipper_5
Note: Cykelväg
AttributeCreator_4
    ATTR_TABLE = SET_TO LOD2 (varchar(8)) = Cykelväg
    -> AttributeFilter_4
Note: Filter på GCM
AttributeFilter_4
    ATTR_NAME = GCM_t_502
    ATTR_VALUES = <Empty>,<Missing>,<Null>,<Unfiltered>,Annan cykelbar förbindelse,Cykelbana, påbjuden,Cykelpassage,Cykelpassage och övergångsställe,Gatupassage utan utmärkning,Gång- och cykelbana,Gång- och cykelbana, uppdelad,Övergångsställe
    Annan cykelbar förbindelse -> Junction_3
    Cykelbana, påbjuden -> Junction_3
    Cykelpassage -> Junction_3
    Gatupassage utan utmärkning -> Junction_3
    Gång- och cykelbana -> Junction_3
    Gång- och cykelbana, uppdelad -> Junction_3
Note: Gångväg
AttributeCreator_5
    ATTR_TABLE = SET_TO LOD2 (varchar(8)) = Gångväg
    -> AttributeFilter_5
Note: Filter på GCM
AttributeFilter_5
    ATTR_NAME = GCM_t_502
    ATTR_VALUES = <Empty>,<Missing>,<Null>,<Unfiltered>,Gatupassage utan utmärkning,Gångbana,Torg/Öppen yta,Trappa,Övergångsställe
    Gatupassage utan utmärkning -> Tester_2
    Gångbana -> Junction_2
    Torg/Öppen yta -> Junction_2
    Trappa -> Junction_2
Note: Två specfika som behövs
Tester_2
    BOOL_OP = OR
    TEST_CLAUSE:
      TEST @Value(ROUTE_ID) = 19194:162919
      TEST @Value(ROUTE_ID) = 19194:153849
    TEST_MODE = TEST
    PASSED -> Junction_2

Bookmark: Körbana
Note: Korta ner linjerna
Snipper_2
    DEAGGREGATE_INPUT = YES
    ENDLOCATIONATTR = @Evaluate(@Length()-1)
    MEASUREMENTTYPE = 2D
    SNIP_MODE = DISTANCE
    STARTLOCATIONATTR = 1
    SNIPMODE = Distance (Value)
    -> Bufferer_3
    -> SpatialFilter_2 [Filter]
Note: Buffra linjerna
Bufferer_3
    ANGLE = 22.5
    CAP_STYLE_LOOKUP = CAP_ROUND
    CORNER_STYLE_LOOKUP = JOIN_ROUND
    MODE = AREA
    OFFSET = .01
    OFFSET_UNITS = NONE
    PRECISION = APPROX
    CAP_STYLE = Round
    CORNER_STYLE = Round
    BUFFERED -> Densifier
Note: Öka antalet vertices
Densifier
    INTERVAL = 1
    MODE_LOOKUP = xy_uniform
    MODE = Uniform Interval
    DENSIFIED -> Chopper
Note: Gör linjerna till punkter enligt vertices
Chopper
    DEAGGREGATE_INPUT = Deaggregate
    MAX_VERTICES = 1
    MODE_LOOKUP = VERTEX
    REMNANT_ATTR = _remnant
    MODE = By Vertex
    CHOPPED -> VoronoiDiagrammer [POINTS]
Note: Skapa voronoi diagram
VoronoiDiagrammer
    ACCUM_ATTRS_NAME = Use Attributes From One Feature
    VORONOI_RADIAL_LIMIT = 30
    VORONOI_POLYGONS -> LineOnAreaOverlayer [AREA]
Note: Overlayer med BK
LineOnAreaOverlayer
    CLEANING_TOLERANCE_LOOKUP = AUTO
    DEAGGREGATE_INPUT = Yes
    OVERLAY_TYPE = AREA_ON_LINE
    OV_ATTR = _overlaps
    CLEANING_TOLERANCE = Automatic
    LINE -> LineOnAreaOverlayer_2 [LINE]
    AREA -> Dissolver
Note: Ena ytorna
Dissolver
    ACCUM_INPUT_ATTRS = Use Attributes From One Feature
    CLEANING_TOLERANCE_LOOKUP = AUTO
    CONNECT_Z_MODE_LOOKUP = FIRST_WINS
    DEAGGREGATE_INPUT = Yes
    GROUP_BY = ROUTE_ID
    CLEANING_TOLERANCE = Automatic
    CONNECT_Z_MODE = First Wins
    AREA -> LineOnAreaOverlayer_2 [AREA]
Note: Overlayer med BK
LineOnAreaOverlayer_2
    CLEANING_TOLERANCE_LOOKUP = AUTO
    DEAGGREGATE_INPUT = Yes
    OVERLAY_TYPE = AREA_ON_LINE
    OV_ATTR = _overlaps
    CLEANING_TOLERANCE = Automatic
    AREA -> SpatialFilter_2 [Candidate]
Note: Ytorna som korsas av NVDB_länkarna
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> ArcStroker_3
Note: Snygga till
ArcStroker_3
    MAKE_POLY = No
    NUM = 50
    STROKE_MODE = NUM_EDGES
    STROKE_CHOICE = Number of Interpolated Edges
    STROKED -> Clipper [CLIPPER]
    STROKED -> Clipper_2 [CLIPPER]
    STROKED -> Clipper_3 [CLIPPER]
    STROKED -> Clipper_6 [CLIPPER]
    STROKED -> AttributeCreator_3

Bookmark: Hierarkisk klippning av transportytor
Note: Körbana
AttributeCreator_3
    ATTR_TABLE = SET_TO LOD2 (varchar(7)) = Körbana
    -> AttributeFilter_2
Note: Körbana > Infart
Clipper_6
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Clipper_7 [CLIPPER]
    OUTSIDE -> Clipper_8 [CLIPPER]
    OUTSIDE -> Clipper_9 [CLIPPER]
    OUTSIDE -> AttributeCreator_2
Note: Infart
AttributeCreator_2
    ATTR_TABLE:
      SET_TO Vagtr_474 (varchar(18)) = Infart
      SET_TO LOD2 (varchar(6)) = Infart
    -> AttributeFilter_2
Note: Körbana > Cykelbana
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Clipper_9 [CANDIDATE]
Note: Infart > Cykelbana
Clipper_9
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Clipper_11 [CANDIDATE]
Note: Körbana > Gångbana
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Clipper_7 [CANDIDATE]
Note: Infart > Gångbana
Clipper_7
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Clipper_10 [CANDIDATE]
Note: Körbana > GC-väg
Clipper_3
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Clipper_8 [CANDIDATE]
Note: Infart > GC-väg
Clipper_8
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> AttributeFilter_2
    OUTSIDE -> Clipper_10 [CLIPPER]
    OUTSIDE -> Clipper_11 [CLIPPER]
Note: GC-väg > Cykelbana
Clipper_11
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> AttributeFilter_2
Note: GC-väg > Gångbana
Clipper_10
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> AttributeFilter_2

Bookmark: Skapa transportytor - Infart
Note: Korta ner linjerna
Snipper_5
    DEAGGREGATE_INPUT = YES
    ENDLOCATIONATTR = @Evaluate(@Length()-1)
    MEASUREMENTTYPE = 2D
    SNIP_MODE = DISTANCE
    STARTLOCATIONATTR = 1
    SNIPMODE = Distance (Value)
    -> Bufferer_5
    -> SpatialFilter_5 [Filter]
Note: Buffra linjerna
Bufferer_5
    ANGLE = 22.5
    CAP_STYLE_LOOKUP = CAP_ROUND
    CORNER_STYLE_LOOKUP = JOIN_ROUND
    MODE = AREA
    OFFSET = .01
    OFFSET_UNITS = NONE
    PRECISION = APPROX
    CAP_STYLE = Round
    CORNER_STYLE = Round
    BUFFERED -> Densifier_4
Note: Öka antalet vertices
Densifier_4
    INTERVAL = 1
    MODE_LOOKUP = xy_uniform
    MODE = Uniform Interval
    DENSIFIED -> Chopper_4
Note: Gör linjerna till punkter enligt vertices
Chopper_4
    DEAGGREGATE_INPUT = Deaggregate
    MAX_VERTICES = 1
    MODE_LOOKUP = VERTEX
    REMNANT_ATTR = _remnant
    MODE = By Vertex
    CHOPPED -> VoronoiDiagrammer_4 [POINTS]
Note: Skapa voronoi diagram
VoronoiDiagrammer_4
    ACCUM_ATTRS_NAME = Use Attributes From One Feature
    VORONOI_RADIAL_LIMIT = 30
    VORONOI_POLYGONS -> LineOnAreaOverlayer_7 [AREA]
Note: Overlayer med BK
LineOnAreaOverlayer_7
    CLEANING_TOLERANCE_LOOKUP = AUTO
    DEAGGREGATE_INPUT = Yes
    OVERLAY_TYPE = AREA_ON_LINE
    OV_ATTR = _overlaps
    CLEANING_TOLERANCE = Automatic
    LINE -> LineOnAreaOverlayer_8 [LINE]
    AREA -> Dissolver_4
Note: Ena ytorna
Dissolver_4
    ACCUM_INPUT_ATTRS = Use Attributes From One Feature
    CLEANING_TOLERANCE_LOOKUP = AUTO
    CONNECT_Z_MODE_LOOKUP = FIRST_WINS
    DEAGGREGATE_INPUT = Yes
    GROUP_BY = ROUTE_ID
    CLEANING_TOLERANCE = Automatic
    CONNECT_Z_MODE = First Wins
    AREA -> LineOnAreaOverlayer_8 [AREA]
Note: Overlayer med BK
LineOnAreaOverlayer_8
    CLEANING_TOLERANCE_LOOKUP = AUTO
    DEAGGREGATE_INPUT = Yes
    OVERLAY_TYPE = AREA_ON_LINE
    OV_ATTR = _overlaps
    CLEANING_TOLERANCE = Automatic
    AREA -> SpatialFilter_5 [Candidate]
Note: Ytorna som korsas av NVDB_länkarna
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> ArcStroker_4
Note: Snygga till
ArcStroker_4
    MAKE_POLY = No
    NUM = 50
    STROKE_MODE = NUM_EDGES
    STROKE_CHOICE = Number of Interpolated Edges
    STROKED -> Clipper_6 [CANDIDATE]

Bookmark: Skapa transportytor - Cykelväg
Note: Korta ner linjerna
Snipper_3
    DEAGGREGATE_INPUT = YES
    ENDLOCATIONATTR = @Evaluate(@Length()-1)
    MEASUREMENTTYPE = 2D
    SNIP_MODE = DISTANCE
    STARTLOCATIONATTR = 1
    SNIPMODE = Distance (Value)
    -> Bufferer_2
    -> SpatialFilter_3 [Filter]
Note: Buffra linjerna
Bufferer_2
    ANGLE = 22.5
    CAP_STYLE_LOOKUP = CAP_ROUND
    CORNER_STYLE_LOOKUP = JOIN_ROUND
    MODE = AREA
    OFFSET = .01
    OFFSET_UNITS = NONE
    PRECISION = APPROX
    CAP_STYLE = Round
    CORNER_STYLE = Round
    BUFFERED -> Densifier_2
Note: Öka antalet vertices
Densifier_2
    INTERVAL = 1
    MODE_LOOKUP = xy_uniform
    MODE = Uniform Interval
    DENSIFIED -> Chopper_2
Note: Gör linjerna till punkter enligt vertices
Chopper_2
    DEAGGREGATE_INPUT = Deaggregate
    MAX_VERTICES = 1
    MODE_LOOKUP = VERTEX
    REMNANT_ATTR = _remnant
    MODE = By Vertex
    CHOPPED -> VoronoiDiagrammer_2 [POINTS]
Note: Skapa voronoi diagram
VoronoiDiagrammer_2
    ACCUM_ATTRS_NAME = Use Attributes From One Feature
    VORONOI_RADIAL_LIMIT = 30
    VORONOI_POLYGONS -> LineOnAreaOverlayer_3 [AREA]
Note: Overlayer med BK
LineOnAreaOverlayer_3
    CLEANING_TOLERANCE_LOOKUP = AUTO
    DEAGGREGATE_INPUT = Yes
    OVERLAY_TYPE = AREA_ON_LINE
    OV_ATTR = _overlaps
    CLEANING_TOLERANCE = Automatic
    LINE -> LineOnAreaOverlayer_4 [LINE]
    AREA -> Dissolver_2
Note: Ena ytorna
Dissolver_2
    ACCUM_INPUT_ATTRS = Use Attributes From One Feature
    CLEANING_TOLERANCE_LOOKUP = AUTO
    CONNECT_Z_MODE_LOOKUP = FIRST_WINS
    DEAGGREGATE_INPUT = Yes
    GROUP_BY = ROUTE_ID
    CLEANING_TOLERANCE = Automatic
    CONNECT_Z_MODE = First Wins
    AREA -> LineOnAreaOverlayer_4 [AREA]
Note: Overlayer med BK
LineOnAreaOverlayer_4
    CLEANING_TOLERANCE_LOOKUP = AUTO
    DEAGGREGATE_INPUT = Yes
    OVERLAY_TYPE = AREA_ON_LINE
    OV_ATTR = _overlaps
    CLEANING_TOLERANCE = Automatic
    AREA -> SpatialFilter_3 [Candidate]
Note: Ytorna som korsas av NVDB_länkarna
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> ArcStroker_2
Note: Snygga till
ArcStroker_2
    MAKE_POLY = No
    NUM = 50
    STROKE_MODE = NUM_EDGES
    STROKE_CHOICE = Number of Interpolated Edges
    STROKED -> AreaOnAreaOverlayer [AREA]
    STROKED -> Clipper [CANDIDATE]

Bookmark: Skapa transportytor - Gångväg
Note: Korta ner linjerna
Snipper_4
    DEAGGREGATE_INPUT = YES
    ENDLOCATIONATTR = @Evaluate(@Length()-1)
    MEASUREMENTTYPE = 2D
    SNIP_MODE = DISTANCE
    STARTLOCATIONATTR = 1
    SNIPMODE = Distance (Value)
    -> Bufferer_4
    -> SpatialFilter_4 [Filter]
Note: Buffra linjerna
Bufferer_4
    ANGLE = 22.5
    CAP_STYLE_LOOKUP = CAP_ROUND
    CORNER_STYLE_LOOKUP = JOIN_ROUND
    MODE = AREA
    OFFSET = .01
    OFFSET_UNITS = NONE
    PRECISION = APPROX
    CAP_STYLE = Round
    CORNER_STYLE = Round
    BUFFERED -> Densifier_3
Note: Öka antalet vertices
Densifier_3
    INTERVAL = 1
    MODE_LOOKUP = xy_uniform
    MODE = Uniform Interval
    DENSIFIED -> Chopper_3
Note: Gör linjerna till punkter enligt vertices
Chopper_3
    DEAGGREGATE_INPUT = Deaggregate
    MAX_VERTICES = 1
    MODE_LOOKUP = VERTEX
    REMNANT_ATTR = _remnant
    MODE = By Vertex
    CHOPPED -> VoronoiDiagrammer_3 [POINTS]
Note: Skapa voronoi diagram
VoronoiDiagrammer_3
    ACCUM_ATTRS_NAME = Use Attributes From One Feature
    VORONOI_RADIAL_LIMIT = 30
    VORONOI_POLYGONS -> LineOnAreaOverlayer_5 [AREA]
Note: Overlayer med BK
LineOnAreaOverlayer_5
    CLEANING_TOLERANCE_LOOKUP = AUTO
    DEAGGREGATE_INPUT = Yes
    OVERLAY_TYPE = AREA_ON_LINE
    OV_ATTR = _overlaps
    CLEANING_TOLERANCE = Automatic
    LINE -> LineOnAreaOverlayer_6 [LINE]
    AREA -> Dissolver_3
Note: Ena ytorna
Dissolver_3
    ACCUM_INPUT_ATTRS = Use Attributes From One Feature
    CLEANING_TOLERANCE_LOOKUP = AUTO
    CONNECT_Z_MODE_LOOKUP = FIRST_WINS
    DEAGGREGATE_INPUT = Yes
    GROUP_BY = ROUTE_ID
    CLEANING_TOLERANCE = Automatic
    CONNECT_Z_MODE = First Wins
    AREA -> LineOnAreaOverlayer_6 [AREA]
Note: Overlayer med BK
LineOnAreaOverlayer_6
    CLEANING_TOLERANCE_LOOKUP = AUTO
    DEAGGREGATE_INPUT = Yes
    OVERLAY_TYPE = AREA_ON_LINE
    OV_ATTR = _overlaps
    CLEANING_TOLERANCE = Automatic
    AREA -> SpatialFilter_4 [Candidate]
Note: Ytorna som korsas av NVDB_länkarna
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> ArcStroker
Note: Snygga till
ArcStroker
    MAKE_POLY = No
    NUM = 50
    STROKE_MODE = NUM_EDGES
    STROKE_CHOICE = Number of Interpolated Edges
    STROKED -> Clipper_2 [CANDIDATE]
    STROKED -> AreaOnAreaOverlayer [AREA]

Bookmark: Skapande av GC-väg
Note: Där Gångväg och Cykelväg overlappar --> GC-väg
AreaOnAreaOverlayer
    ACCUM_ATTRS_NAME = Use Attributes From One Feature
    CLEANING_TOLERANCE_LOOKUP = AUTO
    CONNECT_Z_MODE_LOOKUP = FIRST_WINS
    DEAGGREGATE_INPUT = Yes
    OVC_ATTR = _overlaps
    CLEANING_TOLERANCE = Automatic
    CONNECT_Z_MODE = First Wins
    AREA -> Tester
Note: Tester [Tester] / Test Clauses: Left ValueOperatorRight Value@Value(_overlaps)>1Advanced: / Preserve Feature Order: Per Output Port
Tester
    BOOL_OP = OR
    TEST_CLAUSE = TEST @Value(_overlaps) > 1
    TEST_MODE = TEST
    PASSED -> AttributeCreator
AttributeCreator
    ATTR_TABLE:
      SET_TO Vagtr_474 (varchar(18)) = Gång- och cykelnät
      SET_TO LOD2 (varchar(8)) = GC-väg
    -> Clipper_3 [CANDIDATE]

Bookmark: Färgläggning av ytorna
FeatureColorSetter
    ALGORITHM = MANUAL
    FILL_COLOR = 0,1,1
    MODE = Fixed
    COLORED -> Junction
FeatureColorSetter_2
    ALGORITHM = MANUAL
    FILL_COLOR = 1,0,0
    MODE = Fixed
    COLORED -> Junction
FeatureColorSetter_3
    ALGORITHM = MANUAL
    FILL_COLOR = 0,1,0
    MODE = Fixed
    COLORED -> Junction
FeatureColorSetter_4
    ALGORITHM = MANUAL
    FILL_COLOR = 1,0.666667,0
    MODE = Fixed
    COLORED -> Junction
FeatureColorSetter_5
    ALGORITHM = MANUAL
    FILL_COLOR = 1,0.666667,1
    MODE = Fixed
    COLORED -> Junction

Bookmark: Ta bort för stora ytor
Note: Beräkna area
AreaCalculator
    AREA_ATTR = _area
    AREA_TYPE = Plane Area
    MULT = 1
    -> Tester_27
Note: Tester_27 [Tester] / Test Clauses: Left ValueOperatorRight Value@Value(_area)<3900Advanced: / Preserve Feature Order: Per Output Port
Tester_27
    BOOL_OP = OR
    TEST_CLAUSE = TEST @Value(_area) < 3900
    TEST_MODE = TEST
    PASSED -> Junction_5
    FAILED -> LengthCalculator
    FAILED -> BoundingBoxAccumulator
    FAILED -> FeatureMerger [REQUESTOR]
Note: Ta fram BBOX
BoundingBoxAccumulator
    ACCUM_ATTRS_NAME = Use Attributes From One Feature
    GROUP_BY = _area
    BOUNDING_BOX -> AreaCalculator_2
Note: Beräkna arean för BBOX
AreaCalculator_2
    AREA_ATTR = _bbox
    AREA_TYPE = Plane Area
    MULT = 1
    -> FeatureMerger [SUPPLIER]
Note: FeatureMerger [FeatureMerger] / Transformer Mode: / Suppliers First: No / Join On: RequestorSupplierComparison Mode@Value(_area)@Value(_area)AutomaticMerge Parameters: / Feature Merge Type: Attributes Only / Reject Null and Missing Keys: No / Attribute Accumulation: / Accumulation Mode: Merge Supplier / Conflict Resolution: Use Requestor / Ignore Nulls: No / Advanced: / Preserve Feature Order: Per Output Port
FeatureMerger
    ATTR_ACCUM_MODE = Merge Supplier
    ATTR_CONFLICT_RES_LOOKUP = REQUESTOR_IF_CONFLICT
    IGNORE_NULLS = No
    JOIN_KEYS = @Value(_area) @Value(_area) AUTO
    MERGE_TYPE = Attributes Only
    PROCESS_DUPS = NO
    REJECT_NULL_MISSING_KEYS = No
    SUPPLIERS_FIRST = No
    ATTR_CONFLICT_RES = Use Requestor
    MERGED -> FeatureMerger_2 [REQUESTOR]
Note: Beräkna omkretsen på ytorna
LengthCalculator
    DIM = 2
    LEN_ATTR = _length
    MULT = 1
    -> ExpressionEvaluator
Note: Vägar får lägre jämförelsekvot
ExpressionEvaluator
    ACTION = Create New Attribute
    EXPRESSION = @div(@Value(_area),@pow(@Value(_length),2))
    VAL_ATTR = _Compactness
    -> FeatureMerger_2 [SUPPLIER]
Note: FeatureMerger_2 [FeatureMerger] / Transformer Mode: / Suppliers First: No / Join On: RequestorSupplierComparison Mode@Value(_area)@Value(_area)AutomaticMerge Parameters: / Feature Merge Type: Attributes Only / Reject Null and Missing Keys: No / Attribute Accumulation: / Accumulation Mode: Merge Supplier / Conflict Resolution: Use Requestor / Ignore Nulls: No / Advanced: / Preserve Feature Order: Per Output Port
FeatureMerger_2
    ATTR_ACCUM_MODE = Merge Supplier
    ATTR_CONFLICT_RES_LOOKUP = REQUESTOR_IF_CONFLICT
    IGNORE_NULLS = No
    JOIN_KEYS = @Value(_area) @Value(_area) AUTO
    MERGE_TYPE = Attributes Only
    PROCESS_DUPS = NO
    REJECT_NULL_MISSING_KEYS = No
    SUPPLIERS_FIRST = No
    ATTR_CONFLICT_RES = Use Requestor
    MERGED -> Tester_28
Note: Filter på jämförelsekvot
Tester_28
    BOOL_OP = AND
    TEST_CLAUSE:
      TEST @Value(_bbox) > 0.8
      TEST @Value(_Compactness) < 0.005
    TEST_MODE = TEST
    PASSED -> Junction_5

Bookmark: 3_SKAPA_YTOR_TRÄNINGSOMRÅDE_KISTA
NewFeatureType (writer FFS_3) [off]
    attributes: Vagtr_474 varchar(10), LOD2 varchar(6), ROUTE_ID varchar(38), Typ_512 varchar(23), GCM_t_502 varchar(37), Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer,
      FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40),
      BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)

Bookmark: 3_SKAPA_YTOR_TESTOMRÅDE_KISTA
NewFeatureType (writer FFS_6) [off]
    attributes: Vagtr_474 varchar(10), LOD2 varchar(6), ROUTE_ID varchar(38), Typ_512 varchar(23), GCM_t_502 varchar(37), Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer,
      FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40),
      BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)

Bookmark: 3_SKAPA_YTOR_TESTOMRÅDE_KUNGSHOLMEN
NewFeatureType (writer FFS_10) [off]
    attributes: Vagtr_474 varchar(10), LOD2 varchar(6), ROUTE_ID varchar(38), Typ_512 varchar(23), GCM_t_502 varchar(37), Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer,
      FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40),
      BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)

FME custom transformer SmartCleaner_2013
SmartCleaner adds two new capabilities to the Intersector - extending undershot lines to intersection and deleting overshoots shorter than a specified length. 
Both the undershoot and overshoot tolerances may be taken from a feature attribute or a keyin. This transformer works only on lines, all other features are sent to the <REJECTED> port.
See http://knowledge.safe.com/articles/How_To/Example-of-the-SmartCleaner-Custom-Transformer for more information.
The transformer has two parameters:
    Extension Length:
The distance to extend undershot lines in order to intersect another line.
    Overshoot Length:
The minimum length a dangling line must be in order to be retained.

Parameters:
- LEN = 1   # Extension Length
- VAL = 1   # Overshoot Length

INPUT (input)
    -> GeometryFilter
Note: Route any non-line features / to rejected port
GeometryFilter
    BREAK_AGG = No
    POINT -> <REJECTED> (output)
    LINE -> GeometryValidator
    ARC -> <REJECTED> (output)
    AREA -> <REJECTED> (output)
    ELLIPSE -> <REJECTED> (output)
    TEXT -> <REJECTED> (output)
    RASTER -> <REJECTED> (output)
    POINTCLOUD -> <REJECTED> (output)
    SURFACE -> <REJECTED> (output)
    SOLID -> <REJECTED> (output)
    COLLECTION -> <REJECTED> (output)
    NULL -> <REJECTED> (output)
    INSTANCE -> <REJECTED> (output)
Note: Fix geometry problems
GeometryValidator
    ARC_ENDPOINT_TOLERANCE_MODE = Auto
    CHECK_HOLE_TOUCHING_POLYGON = No
    CONSECUTIVE_IDENTICAL_VERTICES_2D = CONSECUTIVE_IDENTICAL_VERTICES_2D
    DUP_COORDS_CHECK_Z = No
    MISSING_TEXTURE_COORDINATES = MISSING_TEXTURE_COORDINATES
    MISSING_VERTEX_NORMALS = MISSING_VERTEX_NORMALS
    NAN_REMOVAL = NAN_REMOVAL
    NULL_REMOVAL = NULL_REMOVAL
    OGC_SIMPLE_CHECK = OGC_SIMPLE_CHECK
    OGC_VALID_CHECK = OGC_VALID_CHECK
    PLANAR_SURFACE = PLANAR_SURFACE
    PLANAR_TOLERANCE_MODE = Auto
    PRESETS = All
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%MISSING_VERTEX_NORMALS%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"
    SELF_INTERSECTING = SELF_INTERSECTING
    SHELL_VALIDATION = SHELL_VALIDATION
    SOLID_VOID_REPAIR = SOLID_VOID_REPAIR
    TYPE_REPAIR = TYPE_REPAIR
    PASSED -> Intersector
    FAILED -> Intersector
    REPAIRED -> Intersector
Note: Intersect lines
Intersector
    IGNORE_HEIGHTS = YES
    OV_ATTR = _overlaps
    PERFORM_SELF_INTERSECTION = No
    SEG_ATTR = _segments
    SEPARATE_COLLINEAR_SEGMENTS = No
    DUPLICATE_Z_NODES = No
    INTERSECTED -> TopologyBuilder [LINE]
Note: Create node/line / topology to query
TopologyBuilder
    ALLOW_CYCLES = No
    CLEAN_DATA = Yes
    MAX = 0
    OVERLAPPING_MODE = No
    PROP_ATTRS = No
    START_EDGES = No
    ALL_EDGES = Yes
    LINE -> Cloner
    LINE -> TestFilter_2
Note: Find dangling lines to extend
TestFilter_2
    DEFAULT_VALUE = <UNFILTERED>
    TEST_LIST:
      BOOL_OP,AND,COMPOSITE_TEST,<Unused>,TEST_CLAUSE,"TEST @Evaluate(abs(@Value(_right_edge))) = @Value(_arc_id)
      TEST @Evaluate(abs(@Value(_left_edge))) = @Value(_arc_id)",BOTH,BOOL_OP,AND,COMPOSITE_TEST,<Unused>,TEST_CLAUSE,"TEST @Evaluate(abs(@Value(_left_edge))) = @Value(_arc_id)",BEGINNING,BOOL_OP,AND,COMPOSITE_TEST,<Unused>,TEST_CLAUSE,"TEST @Evaluate(abs(@Value(_right_edge))) = @Value(_arc_id)",END
    BOTH -> Extender
    BOTH -> Extender_2
    BEGINNING -> Extender
    END -> Extender_2
Note: Attached to other lines only / at the end, so extend start / of line
Extender
    LEN = $(LEN)
    NUM_SEGS = 1
    BEGINNING -> AttributeCreator_2
Note: Attached to other lines only / at the start, so extend end / of line
Extender_2
    LEN = $(LEN)
    NUM_SEGS = 1
    END -> AttributeCreator_2
Note: Flag extensions for / future cleanup
AttributeCreator_2
    ATTR_LIST = _smartcleaner_extended,1
    -> AttributeRemover_3
Note: Attached at both / ends, so no extension
Cloner
    COPIES = 1
    COPYATT = _copynum
    COPY -> AttributeRemover_3
Note: Clean up unneeded / attributes
AttributeRemover_3
    REMOVE_ATTRS = _overlaps,_segments,_arc_id,_right_polygon,_left_polygon,_right_edge,_left_edge,_from_node,_to_node,_polygons,_copynum
    -> GeometryValidator_2
Note: Fix geometry problems
GeometryValidator_2
    ARC_ENDPOINT_TOLERANCE_MODE = Auto
    CHECK_HOLE_TOUCHING_POLYGON = No
    CONSECUTIVE_IDENTICAL_VERTICES_2D = CONSECUTIVE_IDENTICAL_VERTICES_2D
    DUP_COORDS_CHECK_Z = No
    MISSING_TEXTURE_COORDINATES = MISSING_TEXTURE_COORDINATES
    MISSING_VERTEX_NORMALS = MISSING_VERTEX_NORMALS
    NAN_REMOVAL = NAN_REMOVAL
    NULL_REMOVAL = NULL_REMOVAL
    OGC_SIMPLE_CHECK = OGC_SIMPLE_CHECK
    OGC_VALID_CHECK = OGC_VALID_CHECK
    PLANAR_SURFACE = PLANAR_SURFACE
    PLANAR_TOLERANCE_MODE = Auto
    PRESETS = All
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%MISSING_VERTEX_NORMALS%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"
    SELF_INTERSECTING = SELF_INTERSECTING
    SHELL_VALIDATION = SHELL_VALIDATION
    SOLID_VOID_REPAIR = SOLID_VOID_REPAIR
    TYPE_REPAIR = TYPE_REPAIR
    PASSED -> Intersector_2
    FAILED -> Intersector_2
    REPAIRED -> Intersector_2
Note: Intersect lines and extensions
Intersector_2
    IGNORE_HEIGHTS = YES
    OV_ATTR = _overlaps
    PERFORM_SELF_INTERSECTION = No
    SEG_ATTR = _segments
    SEPARATE_COLLINEAR_SEGMENTS = No
    DUPLICATE_Z_NODES = No
    INTERSECTED -> TopologyBuilder_2 [LINE]
Note: Recreate query topology
TopologyBuilder_2
    ALLOW_CYCLES = No
    CLEAN_DATA = Yes
    MAX = 0
    OVERLAPPING_MODE = No
    PROP_ATTRS = No
    START_EDGES = No
    ALL_EDGES = Yes
    LINE -> Tester
Note: Remove extended dangles
Tester
    BOOL_OP = COMPOSITE
    COMPOSITE_TEST = "(1 OR 2) AND 3"
    TEST_CLAUSE:
      TEST @Evaluate(abs(@Value(_left_edge))) = @Value(_arc_id)
      TEST @Evaluate(abs(@Value(_right_edge))) = @Value(_arc_id)
      TEST @Value(_smartcleaner_extended) = 1
    TEST_MODE = Automatic
    FAILED -> AttributeRemover
Note: Clean up attributes
AttributeRemover
    REMOVE_ATTRS = _overlaps,_segments,_arc_id,_right_polygon,_left_polygon,_right_edge,_left_edge,_from_node,_to_node,_polygons
    -> TopologyBuilder_3 [LINE]
Note: Recreate query topology / with extensions removed
TopologyBuilder_3
    ALLOW_CYCLES = No
    CLEAN_DATA = Yes
    MAX = 0
    OVERLAPPING_MODE = No
    PROP_ATTRS = No
    START_EDGES = No
    ALL_EDGES = Yes
    LINE -> LengthCalculator
Note: Calculate line length
LengthCalculator
    DIM = 2
    LEN_ATTR = _length
    MULT = 1
    -> Tester_2
Note: Remove any dangling / lines less than Overshoot / Length
Tester_2
    BOOL_OP = COMPOSITE
    COMPOSITE_TEST = "(1 OR 2) AND 3"
    TEST_CLAUSE:
      TEST @Evaluate(abs(@Value(_left_edge))) = @Value(_arc_id)
      TEST @Evaluate(abs(@Value(_right_edge))) = @Value(_arc_id)
      TEST @Value(_length) < $(VAL)
    TEST_MODE = Automatic
    FAILED -> AttributeRemover_2
Note: Clean up attributes
AttributeRemover_2
    REMOVE_ATTRS = _smartcleaner_extended,_arc_id,_right_polygon,_left_polygon,_right_edge,_left_edge,_from_node,_to_node,_polygons,_length
    -> CLEANED (output)
CLEANED (output)
<REJECTED> (output)
