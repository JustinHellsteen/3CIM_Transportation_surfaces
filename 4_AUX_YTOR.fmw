FME workspace 4_AUX_YTOR.fmw

Parameters:
- SourceDataset_FFS = C:\Users\ai31986\HCP\Examensarbete\FME Projekt workspaces\3_SKAPA_TRANSPORTYTOR\OUTPUT\3_SKAPA_TRANSPORTYTOR.ffs   # Source FME Feature Store (FFS) File(s)
- SourceDataset_FFS_7 = C:\Users\ai31986\HCP\Examensarbete\FME Projekt workspaces\2_BK_CLEAN\OUTPUT\2_BK_CLEAN.ffs   # Source FME Feature Store (FFS) File(s)
- SourceDataset_DGNV8 = C:\Users\ai31986\HCP\Examensarbete\Data\Ramar\Urklipp runt Kistaäng.dgn   # Source Bentley MicroStation Design File(s)
- DestDataset_FFS = $(FME_MF_DIR)OUTPUT\4_MERGE_TRANSPORTYTOR.ffs   # Destination FME Feature Store (FFS) File
- SourceDataset_FFS_4 = C:\Users\ai31986\HCP\Examensarbete\FME Projekt workspaces\2_BK_CLEAN\OUTPUT\VERIF_2_BK_CLEAN.ffs   # Source FME Feature Store (FFS) File(s)
- SourceDataset_FFS_13 = C:\Users\ai31986\HCP\Examensarbete\FME Projekt workspaces\3_SKAPA_TRANSPORTYTOR\OUTPUT\VERIF_3_SKAPA_TRANSPORTYTOR.ffs   # Source FME Feature Store (FFS) File(s)
- SourceDataset_FFS_11 = C:\Users\ai31986\HCP\Examensarbete\Data\Ramar\VERIF.ffs   # Source FME Feature Store (FFS) File(s)
- DestDataset_FFS_2 = $(FME_MF_DIR)OUTPUT\VERIF_4_MERGE_TRANSPORTYTOR.ffs   # Destination FME Feature Store (FFS) File
- SourceDataset_FFS_15 = C:\Users\ai31986\HCP\Examensarbete\Data\Ramar\RAM_KUNGSHOLMEN.ffs   # Source FME Feature Store (FFS) File(s)
- SourceDataset_FFS_12 = C:\Users\ai31986\HCP\Examensarbete\FME Projekt workspaces\3_SKAPA_TRANSPORTYTOR\OUTPUT\3_SKAPA_TRANSPORTYTOR_KUNGSHOLMEN.ffs   # Source FME Feature Store (FFS) File(s)
- SourceDataset_FFS_14 = C:\Users\ai31986\HCP\Examensarbete\FME Projekt workspaces\2_BK_CLEAN\OUTPUT\2_BK_CLEAN_KUNGSHOLMEN.ffs   # Source FME Feature Store (FFS) File(s)
- DestDataset_FFS_3 = $(FME_MF_DIR)OUTPUT\4_MERGE_TRANSPORTYTOR_KUNGSHOLMEN.ffs   # Destination FME Feature Store (FFS) File

Readers:
- FFS_1: FFS from $(SourceDataset_FFS) in SWEREF-99-18-00
- FFS_2: FFS from $(SourceDataset_FFS_7) in SWEREF-99-18-00
- DGNV8_1: DGNV8 from $(SourceDataset_DGNV8) in SWEREF-99-18-00
- FFS_3: FFS from $(SourceDataset_FFS_4) in SWEREF-99-18-00
- FFS_5: FFS from $(SourceDataset_FFS_13) in SWEREF-99-18-00
- FFS_6: FFS from $(SourceDataset_FFS_11) in SWEREF-99-18-00
- FFS_8: FFS from $(SourceDataset_FFS_15) in SWEREF-99-18-00
- FFS_9: FFS from $(SourceDataset_FFS_12) in SWEREF-99-18-00
- FFS_10: FFS from $(SourceDataset_FFS_14) in SWEREF-99-18-00

Writers:
- FFS_4: FFS to $(DestDataset_FFS) in SWEREF-99-18-00
- FFS_7: FFS to $(DestDataset_FFS_2) in SWEREF-99-18-00
- FFS_11: FFS to $(DestDataset_FFS_3) in SWEREF-99-18-00

Note: Skapa ytor
AreaBuilder
    ALLOW_CYCLES = No
    CHECK_CURVE_DIRECTION = No
    CONNECT_Z_MODE_LOOKUP = FIRST_WINS
    CONSIDER_NODE_ELEVATION_LOOKUP = NO
    DEAGGREGATE_INPUT = Deaggregate
    DONUT_CREATION = Yes
    DROP_HOLES = No
    LINES_AS_SEGMENTS = No
    POLY_ACCUM_ATTRS_NAME = Use Attributes From One Feature
    SNAPTYPE = NONE
    CONNECT_Z_MODE = First Wins
    CONSIDER_NODE_ELEVATION = no
    SNAPTYPE_PARAM = None
    AREA -> AttributeFilter_2
    Incomplete -> AttributeFilter_2
AttributeFilter_2
    ATTR_NAME = DP_SUBTYPE_NAME
    ATTR_VALUES = <Empty>,<Missing>,<Null>,<Unfiltered>,Refug,Regnskydd,Vägutbredning
    Refug -> AttributeCreator
    Regnskydd -> Junction_22
    Vägutbredning -> Junction_24
Note: Tester : Input
Junction_22
    -> Junction_23
Note: Clipper_3 : Candidate
Junction_24
    -> Junction_25
Note: AttributeFilter_2 : Vägutbredning
Junction_25
    -> Clipper_3 [CANDIDATE]
AttributeFilter
    ATTR_NAME = LOD2
    ATTR_VALUES = <Empty>,<Missing>,<Null>,<Unfiltered>,Cykelväg,GC-väg,Gångväg,Infart,Körbana
    Cykelväg -> Junction
    GC-väg -> Junction
    Gångväg -> Junction
    Infart -> AttributeManager
    Körbana -> AreaCalculator_3
    Körbana -> Junction_5
Note: AttributeCreator : Output
Junction_21
    -> Junction_4
Junction_5
    -> Intersector
    -> Junction_14
    -> Junction_16
Junction_16
    -> Junction_17
Note: Clipper : Clipper
Junction_14
    -> Junction_15
Note: Addera hjälpattribut
AttributeManager
    ATTR_TABLE:
      SET_TO LOD2 (varchar(7)) = Körbana
      SET_TO LOD3 (varchar(11)) = Ej Huvudled
    -> Junction
Note: Junction_7 : Input
Junction
    -> Junction_18
    -> Junction_26
Note: Junction_9 : Output
Junction_18
    -> Junction_7
Note: Junction_10 : Input
Junction_26
    -> Junction_27
Note: Junction : Output
Junction_27
    -> Clipper_5 [CLIPPER]
Junction_10
    -> Intersector
Junction_4
    -> Clipper_3 [CLIPPER]
    -> Bufferer
    -> Junction_7
Note: Skapa buffer av körbana för klippning av auxiliary ytor
Bufferer
    ANGLE = 22.5
    CAP_STYLE_LOOKUP = CAP_ARC
    CORNER_STYLE_LOOKUP = JOIN_ARC
    MODE = AREA
    OFFSET = 10
    OFFSET_UNITS = NONE
    PRECISION = APPROX
    CAP_STYLE = Arc
    CORNER_STYLE = Arc
    BUFFERED -> Clipper_4 [CLIPPER]
Junction_6
    -> Clipper_4 [CANDIDATE]
Note: Klippning för att hitta auxiliary ytor
Clipper_4
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Clipper_5 [CANDIDATE]
Junction_7
    -> Clipper_6 [CANDIDATE]
Note: Klipp auxiliary och körbana mot regnskydd
Clipper_6
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Junction_8
Junction_8
    -> AttributeRemover
Note: Ta bort onödiga attribut
AttributeRemover
    REMOVE_ATTRS = _area,_bbox,_clipped,_Compactness,_length,_overlaps,_predicate,_remnant,_result,_segments
    -> AttributeCreator_4
Note: Tilldela LOD1 attribut
AttributeCreator_4
    ATTR_TABLE = SET_TO LOD1 (varchar(9)) = Vägtrafik
    -> AttributeFilter_3
AttributeFilter_3
    ATTR_NAME = LOD2
    ATTR_VALUES = <Empty>,<Missing>,<Null>,<Unfiltered>,Cykelväg,GC-väg,Gångväg,Infart,Körbana,Separering
    <MISSING> -> Odefinierat
    Cykelväg -> Cykelväg
    GC-väg -> GC-väg
    Gångväg -> Gångväg
    Körbana -> Körbana
    Separering -> AttributeFilter_4
Note: ta bort duppletter
Matcher
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = LOD2
    MATCH_STRATEGY_LOOKUP = MATCH
    MATCH_STRATEGY = Match Selected Attributes
    SINGLE_MATCHED -> Junction_12
    NOT_MATCHED -> Junction_12
Junction_12
    -> Counter
Junction_13
    -> AttributeRemover_3
Note: Ta bort oönskade attribut
AttributeRemover_3
    LIST_ATTRS = _histogram{} _histogram{}.count _histogram{}.value _relationships{} _relationships{}.Användningstyp _relationships{}.de9im _relationships{}.pass{}
    REMOVE_ATTRS = _histogram{0}.count,_histogram{0}.value,_match_id,_related_suppliers,_relationships{0}.Användningstyp,_relationships{0}.de9im,_relationships{0}.pass{0}
    -> NewFeatureType (writer FFS_4)
    -> NewFeatureType (writer FFS_7)
    -> NewFeatureType (writer FFS_11)

Bookmark: 2_BK_CLEAN_TRÄNINGSOMRÅDE_KISTA
NewFeatureType (reader FFS_2) [off]
    attributes: DP_SUBTYPE_NAME buffer
    -> AreaBuilder

Bookmark: 2_BK_CLEAN_TESTOMRÅDE_KISTA
NewFeatureType (reader FFS_3) [off]
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> AreaBuilder

Bookmark: 2_BK_CLEAN_TESTOMRÅDE_KUNGSHOLMEN
NewFeatureType (reader FFS_10) [off]
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> AreaBuilder

Bookmark: Baka in regnskydd
Note: AttributeFilter_2 : Regnskydd
Junction_23
    -> Tester
Note: Se till att arean är tillräckligt stor, annars felklassad
Tester
    BOOL_OP = OR
    TEST_CLAUSE = TEST @Area() > 10
    TEST_MODE = TEST
    FAILED -> AreaBuilder_3
Note: Säkerställ att de är ytor
AreaBuilder_3
    ALLOW_CYCLES = No
    CHECK_CURVE_DIRECTION = No
    CONNECT_Z_MODE_LOOKUP = FIRST_WINS
    CONSIDER_NODE_ELEVATION_LOOKUP = NO
    DEAGGREGATE_INPUT = Deaggregate
    DONUT_CREATION = Yes
    DROP_HOLES = No
    LINES_AS_SEGMENTS = No
    POLY_ACCUM_ATTRS_NAME = Use Attributes From One Feature
    SNAPTYPE = NONE
    CONNECT_Z_MODE = First Wins
    CONSIDER_NODE_ELEVATION = no
    SNAPTYPE_PARAM = None
    AREA -> Junction_8
    AREA -> Clipper_6 [CLIPPER]

Bookmark: 3_SKAPA_YTOR_TRÄNINGSOMRÅDE_KISTA
NewFeatureType (reader FFS_1) [off]
    attributes: LOD2 varchar(7), ROUTE_ID varchar(38), Typ_512 varchar(23), GCM_t_502 varchar(37), Vagtr_474 varchar(10), _remnant char(3), _overlaps uint32, _predicate buffer, _clipped char(9), _area real64, _bbox real64, _length real64, _Compactness real64
    -> AttributeFilter

Bookmark: 3_SKAPA_YTOR_TESTOMRÅDE_KISTA
NewFeatureType (reader FFS_5) [off]
    attributes: Vagtr_474 varchar(10), LOD2 varchar(6), ROUTE_ID varchar(38), Typ_512 varchar(23), GCM_t_502 varchar(37), Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer,
      FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40),
      BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> AttributeFilter

Bookmark: 3_SKAPA_YTOR_TESTOMRÅDE_KUNGSHOLMEN
NewFeatureType (reader FFS_9) [off]
    attributes: Vagtr_474 varchar(10), LOD2 varchar(6), ROUTE_ID varchar(38), Typ_512 varchar(23), GCM_t_502 varchar(37), Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer,
      FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40),
      BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> AttributeFilter

Bookmark: Hantera refuger
Note: Beräkna area för refugerna
Note: Junction_3 : Input
AreaCalculator_3
    AREA_ATTR = _area
    AREA_TYPE = Plane Area
    MULT = 1
    -> Tester_5
Note: Säkerställ att arean inte är för stor --> felklassad
Tester_5
    BOOL_OP = OR
    TEST_CLAUSE = TEST @Value(_area) < 3
    TEST_MODE = TEST
    PASSED -> AttributeCreator
Note: Skapa attribut för refugerna
AttributeCreator
    ATTR_TABLE:
      SET_TO LOD2 (varchar(10)) = Separering
      SET_TO LOD3 (varchar(5)) = Refug
    -> Junction_20
Note: Junction_4 : Input
Junction_20
    -> Junction_9
    -> Junction_21
Note: Clipper_2 : Clipper
Junction_9
    -> Junction_19

Bookmark: Ta fram körbana samt innehållande separeringsytor
Note: AttributeCreator : Output
Junction_19
    -> Clipper_2 [CLIPPER]
Note: Junction_5 : Output
Junction_17
    -> Junction_3
Note: Junction_5 : Output
Junction_15
    -> Clipper [CLIPPER]
Note: Intersector för att få med urklippet som omringande ram
Intersector
    ATTRS_ACCUM_MODE = Use Attributes From One Feature
    CLEANING_TOLERANCE_LOOKUP = AUTO
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    INTERSECTED -> AreaBuilder_2
Note: Skapa vattentäta ytor med hjälp av ramen
AreaBuilder_2
    ALLOW_CYCLES = No
    CHECK_CURVE_DIRECTION = No
    CONNECT_Z_MODE_LOOKUP = FIRST_WINS
    CONSIDER_NODE_ELEVATION_LOOKUP = NO
    DEAGGREGATE_INPUT = Deaggregate
    DONUT_CREATION = YES
    DROP_HOLES = No
    LINES_AS_SEGMENTS = No
    POLY_ACCUM_ATTRS_NAME = Merge Incoming Attributes
    SNAPTYPE = NONE
    CONNECT_Z_MODE = First Wins
    CONSIDER_NODE_ELEVATION = no
    SNAPTYPE_PARAM = None
    AREA -> LengthCalculator
Note: Beräkna omkrets
LengthCalculator
    DIM = 2
    LEN_ATTR = _length
    MULT = 1
    -> ExpressionEvaluator
Note: Jämför förhållande mellan omrekts och area
ExpressionEvaluator
    ACTION = Create New Attribute
    EXPRESSION = @div(@pow(@Value(_length),2),@Area())
    VAL_ATTR = _result
    -> Tester_2
Note: Ifall förhållandet > ex 50 så har ytan stor omkrets i jämförelse med arean --> Avlång yta
Tester_2
    BOOL_OP = OR
    TEST_CLAUSE = TEST @Value(_result) > 50
    TEST_MODE = TEST
    PASSED -> Junction_2
    FAILED -> Tester_3
Note: Rensa stora ytor av dem som inte fångades i jämförelsen
Tester_3
    BOOL_OP = OR
    TEST_CLAUSE = TEST @Area() < 1100
    TEST_MODE = TEST
    PASSED -> Junction_2
Junction_2
    -> Clipper [CANDIDATE]
Note: Klipp ytorna med den orginella körbanan för att separera ut separeringsytor
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> LengthCalculator_2
Note: Beräkna omkrets
LengthCalculator_2
    DIM = 2
    LEN_ATTR = _length
    MULT = 1
    -> ExpressionEvaluator_2
Note: Jämför förhållande mellan omkrets och area
ExpressionEvaluator_2
    ACTION = Create New Attribute
    EXPRESSION = @div(@pow(@Value(_length),2),@Area())
    VAL_ATTR = _result
    -> Tester_4
Note: Ifall förhållandet > ex 50 så har ytan stor omkrets i jämförelse med arean --> Avlång yta
Tester_4
    BOOL_OP = OR
    TEST_CLAUSE = TEST @Value(_result) > 50
    TEST_MODE = TEST
    PASSED -> AttributeCreator_3
    FAILED -> Tester_6
Note: Återigen, rensa för stora ytor
Tester_6
    BOOL_OP = OR
    TEST_CLAUSE = TEST @Area() < 500
    TEST_MODE = TEST
    PASSED -> AttributeCreator_3
Note: Märk separeringsobjekt med attribut
AttributeCreator_3
    ATTR_TABLE = SET_TO LOD2 (varchar(10)) = Separering
    -> Junction_3
Junction_3
    -> Clipper_2 [CANDIDATE]
Note: Klipp med avseende på refuger
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> AttributeCreator_2
Note: Ge LOD1 attribut
AttributeCreator_2
    ATTR_TABLE = SET_TO LOD1 (varchar(9)) = Vägtrafik
    -> Tester_9
Note: Ta bort de sista för stora ytorna
Tester_9
    BOOL_OP = OR
    TEST_CLAUSE = TEST @Area() < 5000
    TEST_MODE = TEST
    PASSED -> Junction_4

Bookmark: Ram Träningsområde Kista
Default (reader DGNV8_1) [off]
    -> Junction_10

Bookmark: Ram Testområde Kista
VERIF (reader FFS_6) [off]
    attributes: _creation_instance uint64
    -> Junction_10

Bookmark: Ram Testområde Kungsholmen
NewFeatureType (reader FFS_8) [off]
    attributes: _creation_instance uint64
    -> Junction_10

Bookmark: Hitta omringande ytor till körbanan (Auxiliary)
Note: Hitta omringande ytor till körbanan
Clipper_3
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> LengthCalculator_3
Note: Beräkna omkretsen av ytorna
LengthCalculator_3
    DIM = 2
    LEN_ATTR = _length
    MULT = 1
    -> ExpressionEvaluator_3
Note: Jämför omkrets och area
ExpressionEvaluator_3
    ACTION = Create New Attribute
    EXPRESSION = @div(@pow(@Value(_length),2),@Area())
    VAL_ATTR = _result
    -> Tester_7
Note: Filtrera på jämförelsen och area. För stor area och för liten omkrets försvinner
Tester_7
    BOOL_OP = COMPOSITE
    COMPOSITE_TEST = 1 AND 2
    TEST_CLAUSE:
      TEST @Value(_result) > 40
      TEST @Area() < 10000
    TEST_MODE = TEST
    PASSED -> Junction_6
    FAILED -> Tester_8
Note: Behåll små ytor som inte klarade testet
Tester_8
    BOOL_OP = OR
    TEST_CLAUSE = TEST @Area() < 1100
    TEST_MODE = TEST
    PASSED -> Junction_6

Bookmark: Införande av auxiliary ytor
Note: Klipp mot resterande vägtyper
Clipper_5
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Deaggregator
Note: Dela upp ytorna
Deaggregator
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> Tester_11
Note: Ta bort för stora ytor
Tester_11
    BOOL_OP = OR
    TEST_CLAUSE = TEST @Area() < 500
    TEST_MODE = TEST
    PASSED -> Junction_7

Bookmark: Färgsättning
Odefinierat: FeatureColorSetter
    ALGORITHM = MANUAL
    COLOR = 1,0,1
    FILL_COLOR = 1,0,1
    MODE = Fixed
    COLORED -> Junction_11
Cykelväg: FeatureColorSetter
    ALGORITHM = MANUAL
    COLOR = 1,0,0
    FILL_COLOR = 1,0,0
    MODE = Fixed
    COLORED -> Junction_11
GC-väg: FeatureColorSetter
    ALGORITHM = MANUAL
    COLOR = 1,0.666667,0
    FILL_COLOR = 1,0.666667,0
    MODE = Fixed
    COLORED -> Junction_11
Gångväg: FeatureColorSetter
    ALGORITHM = MANUAL
    COLOR = 0.333333,1,0
    FILL_COLOR = 0.333333,1,0
    MODE = Fixed
    COLORED -> Junction_11
Körbana: FeatureColorSetter
    ALGORITHM = MANUAL
    COLOR = 0,1,1
    FILL_COLOR = 0,1,1
    MODE = Fixed
    COLORED -> Junction_11
AttributeFilter_4
    ATTR_NAME = LOD3
    ATTR_VALUES = <Empty>,<Missing>,<Null>,<Unfiltered>,Refug
    <MISSING> -> FeatureColorSetter_7
    Refug -> Refug
FeatureColorSetter_7
    ALGORITHM = MANUAL
    COLOR = 0.666667,0.333333,1
    FILL_COLOR = 0.666667,0.333333,1
    MODE = Fixed
    COLORED -> Junction_11
Refug: FeatureColorSetter
    ALGORITHM = MANUAL
    COLOR = 1,1,1
    FILL_COLOR = 1,1,1
    MODE = Fixed
    COLORED -> Junction_11
Junction_11
    -> Matcher

Bookmark: ID hantering för en specfik yta
Counter
    CNT_ATTR = _count
    DOMAIN = counter
    SCOPE = Global
    START = 0
    -> Tester_10
Tester_10
    BOOL_OP = OR
    TEST_CLAUSE = TEST @Value(_count) = 648
    TEST_MODE = TEST
    PASSED -> AttributeManager_2
    FAILED -> Junction_13
AttributeManager_2
    ATTR_TABLE:
      SET_TO LOD2 (varchar(10)) = Separering
      SET_TO LOD3 (varchar(5)) = Refug
    -> Junction_13

Bookmark: 4_AUX_YTOR_TRÄNINGSOMRÅDE_KISTA
NewFeatureType (writer FFS_4) [off]
    attributes: LOD1 varchar(9), DP_SUBTYPE_NAME buffer, LOD2 varchar(7), LOD3 varchar(5), ROUTE_ID varchar(38), Typ_512 varchar(23), GCM_t_502 varchar(37), Vagtr_474 varchar(10), _part_number uint64, _geometry_name buffer, _count int64, Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200),
      STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), INM_LAGE int32, LANDMARKE int32,
      VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32,
      _right_face uint32, _left_face uint32, _faces uint32, _creation_instance uint64, Added_line varchar(4)

Bookmark: 4_AUX_YTOR_TESTOMRÅDE_KISTA
NewFeatureType (writer FFS_7) [off]
    attributes: LOD1 varchar(9), DP_SUBTYPE_NAME buffer, LOD2 varchar(7), LOD3 varchar(5), ROUTE_ID varchar(38), Typ_512 varchar(23), GCM_t_502 varchar(37), Vagtr_474 varchar(10), _part_number uint64, _geometry_name buffer, _count int64, Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200),
      STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), INM_LAGE int32, LANDMARKE int32,
      VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32,
      _right_face uint32, _left_face uint32, _faces uint32, _creation_instance uint64, Added_line varchar(4)

Bookmark: 4_AUX_YTOR_TESTOMRÅDE_KUNGSHOLMEN
NewFeatureType (writer FFS_11)
    attributes: LOD1 varchar(9), DP_SUBTYPE_NAME buffer, LOD2 varchar(7), LOD3 varchar(5), ROUTE_ID varchar(38), Typ_512 varchar(23), GCM_t_502 varchar(37), Vagtr_474 varchar(10), _part_number uint64, _geometry_name buffer, _count int64, Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200),
      STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), INM_LAGE int32, LANDMARKE int32,
      VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32,
      _right_face uint32, _left_face uint32, _faces uint32, _creation_instance uint64, Added_line varchar(4)
