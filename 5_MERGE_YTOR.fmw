FME workspace 5_MERGE_YTOR.fmw

Parameters:
- SourceDataset_FFS = C:\Users\ai31986\HCP\Examensarbete\FME Projekt workspaces\2_BK_CLEAN\OUTPUT\2_BK_CLEAN.ffs   # Source FME Feature Store (FFS) File(s)
- SourceDataset_DGNV8 = C:\Users\ai31986\HCP\Examensarbete\Data\Ramar\Urklipp runt Kistaäng.dgn   # Source Bentley MicroStation Design File(s)
- SourceDataset_FFS_9 = C:\Users\ai31986\HCP\Examensarbete\FME Projekt workspaces\4_MERGE_TRANSPORTYTOR\OUTPUT\4_MERGE_TRANSPORTYTOR.ffs   # Source FME Feature Store (FFS) File(s)
- SourceDataset_OGCGEOPACKAGE = C:\Users\ai31986\HCP\Examensarbete\Data\Parkdata\TK_Parkkarta_dpMapExport_GPKG_2024-06-12.gpkg   # GeoPackage File
- FEATURE_TYPES =   # " " Feature Types to Read
- SourceDataset_OGCGEOPACKAGE_3 = \\ad.stockholm.se\cli-sd\cc2sd003\006284\Projekt\3CIM\3CIM-IMPLEMENTERING\STHLM_Geodata\Fastigheter\Kvarter.gpkg   # GeoPackage File
- SourceDataset_FFS_5 = C:\Users\ai31986\HCP\Examensarbete\FME Projekt workspaces\1_BK_ATTRIBUTES_FIXED\OUTPUT\1_BK_ATTRIBUTES_FIXED.ffs   # Source FME Feature Store (FFS) File(s)
- DestDataset_FFS = $(FME_MF_DIR)OUTPUT\5_SAMTLIGA_YTOR.ffs   # Destination FME Feature Store (FFS) File
- SourceDataset_OGCGEOPACKAGE_6 = \\ad.stockholm.se\cli-sd\cc2sd003\006284\Projekt\3CIM\3CIM-IMPLEMENTERING\STHLM_Geodata\TK_Parkkarta_dpMapExport_GPKG\TK_Parkkarta_dpMapExport_GPKG_2025-04-03.gpkg   # GeoPackage File
- FEATURE_TYPES_3 =
- SourceDataset_FFS_17 = C:\Users\ai31986\HCP\Examensarbete\FME Projekt workspaces\2_BK_CLEAN\OUTPUT\VERIF_2_BK_CLEAN.ffs   # Source FME Feature Store (FFS) File(s)
- SourceDataset_FFS_21 = C:\Users\ai31986\HCP\Examensarbete\FME Projekt workspaces\4_MERGE_TRANSPORTYTOR\OUTPUT\VERIF_4_MERGE_TRANSPORTYTOR.ffs   # Source FME Feature Store (FFS) File(s)
- SourceDataset_FFS_15 = C:\Users\ai31986\HCP\Examensarbete\Data\Ramar\VERIF.ffs   # Source FME Feature Store (FFS) File(s)
- DestDataset_FFS_2 = $(FME_MF_DIR)OUTPUT\VERIF_5_SAMTLIGA_YTOR.ffs   # Destination FME Feature Store (FFS) File
- SourceDataset_FFS_14 = C:\Users\ai31986\HCP\Examensarbete\FME Projekt workspaces\1_BK_ATTRIBUTES_FIXED\OUTPUT\1_BK_ATTRIBUTES_FIXED_KUNGSHOLMEN.ffs   # Source FME Feature Store (FFS) File(s)
- SourceDataset_FFS_16 = C:\Users\ai31986\HCP\Examensarbete\Data\Ramar\RAM_KUNGSHOLMEN.ffs   # Source FME Feature Store (FFS) File(s)
- SourceDataset_FFS_18 = C:\Users\ai31986\HCP\Examensarbete\FME Projekt workspaces\2_BK_CLEAN\OUTPUT\2_BK_CLEAN_KUNGSHOLMEN.ffs   # Source FME Feature Store (FFS) File(s)
- SourceDataset_FFS_20 = C:\Users\ai31986\HCP\Examensarbete\FME Projekt workspaces\4_MERGE_TRANSPORTYTOR\OUTPUT\4_MERGE_TRANSPORTYTOR_KUNGSHOLMEN.ffs   # Source FME Feature Store (FFS) File(s)
- DestDataset_FFS_3 = $(FME_MF_DIR)OUTPUT\5_SAMTLIGA_YTOR_KUNGSHOLMEN.ffs   # Destination FME Feature Store (FFS) File

Readers:
- FFS_1: FFS from $(SourceDataset_FFS) in SWEREF-99-18-00
- DGNV8_1: DGNV8 from $(SourceDataset_DGNV8) in SWEREF-99-18-00
- FFS_3: FFS from $(SourceDataset_FFS_9) in SWEREF-99-18-00
- OGCGEOPACKAGE_1: OGCGEOPACKAGE from $(SourceDataset_OGCGEOPACKAGE) in SWEREF-99-18-00
- OGCGEOPACKAGE_2: OGCGEOPACKAGE from $(SourceDataset_OGCGEOPACKAGE_3) in SWEREF-99-18-00
- FFS_4: FFS from $(SourceDataset_FFS_5) in SWEREF-99-18-00
- OGCGEOPACKAGE_4: OGCGEOPACKAGE from $(SourceDataset_OGCGEOPACKAGE_6) in SWEREF-99-18-00
- FFS_2: FFS from $(SourceDataset_FFS_17) in SWEREF-99-18-00
- FFS_6: FFS from $(SourceDataset_FFS_21) in SWEREF-99-18-00
- FFS_7: FFS from $(SourceDataset_FFS_15) in SWEREF-99-18-00
- FFS_10: FFS from $(SourceDataset_FFS_14) in SWEREF-99-18-00
- FFS_11: FFS from $(SourceDataset_FFS_16) in SWEREF-99-18-00
- FFS_12: FFS from $(SourceDataset_FFS_18) in SWEREF-99-18-00
- FFS_13: FFS from $(SourceDataset_FFS_20) in SWEREF-99-18-00

Writers:
- FFS_5: FFS to $(DestDataset_FFS) in SWEREF-99-18-00
- FFS_9: FFS to $(DestDataset_FFS_2) in SWEREF-99-18-00
- FFS_14: FFS to $(DestDataset_FFS_3) in SWEREF-99-18-00

GeometryFilter_2
    FILTER_MODE = SIMPLE
    FILTER_MULTI = FILTER_TYPES]"Point Line Area"]FME_CONTROLLER_QUERY_FILE]]FME_CONTROLLER_CHOICE]Simple
    Area -> AreaOnAreaOverlayer [AREA]
Note: Merge BK clean och de mergade transportytorna
AreaOnAreaOverlayer
    ACCUM_ATTRS_NAME = Merge Incoming Attributes
    CLEANING_TOLERANCE_LOOKUP = AUTO
    CONNECT_Z_MODE_LOOKUP = FIRST_WINS
    DEAGGREGATE_INPUT = Yes
    OVC_ATTR = _overlaps
    CLEANING_TOLERANCE = Automatic
    CONNECT_Z_MODE = First Wins
    AREA -> Dissolver
Note: Test för stora slaskytor
Tester
    BOOL_OP = AND
    TEST_CLAUSE:
      TEST @Area() > 10000
      TEST LOD1 ATTRIBUTE_IS_MISSING ""
    TEST_MODE = TEST
    PASSED -> AttributeManager
    FAILED -> Tester_2
AttributeManager
    ATTR_TABLE:
      SET_TO 1_Temaklass (varchar(11)) = Stor yta
      SET_TO 2_Klass (varchar(25)) = Stor yta
      SET_TO 3_Subklass (varchar(27)) = Stor yta
    -> Junction_2
Note: Test för vägbana
Tester_2
    BOOL_OP = OR
    TEST_CLAUSE = TEST LOD1 ATTRIBUTE_HAS_A_VALUE ""
    TEST_MODE = TEST
    PASSED -> AttributeManager_2
    FAILED -> PointOnAreaOverlayer [AREA]
AttributeManager_2
    ATTR_TABLE:
      SET_TO 1_Temaklass (varchar(11)) = Väg
      SET_TO 2_Klass (varchar(25)) = Null
      SET_TO 3_Subklass (varchar(27)) = Null
    -> Junction_2
Note: CenterPointReplacer : Input
Junction_8
    -> Junction_9
GeometryCoercer
    GQUERY:
      for $geom in //geometry
      where $geom/count(parent::geometry) = 0
      return number($geom/@fme_id)
    KIND = fme_line
    COERCED -> LineOnLineOverlayer [LINE]
    COERCED -> LineOnLineOverlayer_2 [LINE]
Note: Klipp mot ramen
Clipper_3
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Junction_6
Note: Clipper_6 : Clipper
Junction_6
    -> Junction_7
Note: Klipp mot ramen
Clipper_4
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> AttributeFilter_4
AttributeFilter_4
    ATTR_NAME = sub_c_type
    ATTR_VALUES = <Empty>,<Missing>,<Null>,<Unfiltered>,Annuellrabatt - gyB,Asfalt parkväg - gyB,Askkopp - sB,Baksand - gyB,Bark/flis (ej plantering) - gyB,Betongplattor - gyB,Bruksbuskage - gyB,Bruksgräsyta - gyB,Bruksmur - gyB,Brukspark - gyB,Bäck, vattendrag - gyB,Dagvattenbrunn - sB,Driftområde - gyB,Död ved/biodepå - sB,Elskåp (service) belysning - sB,Fontän - gyB,Grus parkväg - gyB,Grus, stenmjöl - gyB,Gummibelagd yta - gyB,Gungställningsfack/hänggunga - sB,Gångfålla med grind/bom - sB,Hundrastgård - gyB,Invasiv växt - gyB,Klippt häck - gyB,Kullersten - gyB,Ledstång - glB,Lek- och klätterställning - sB,Lekhus - sB,Luftbrunn - sB,Lökplantering - gyB,Marksten av betong - gyB,Nätstängsel - glB,Okänd - sB,Ospecificerat objekt - gyB,Perenna växter - gyB,Pergola - glB,Prydnadsbuskage - gyB,Rutschbana - sB,Sandlådesarg - glB,Skelettjord - gyB,Skräpkorg - sB,Slyröjd yta - gyB,Slåtter utan uppsamling - gyB,Slåtteräng - gyB,Smågatsten - gyB,Snöröjd sträcka snöröjningsklass 3 - glB,Snöröjd sträcka snöröjningsklass 6 - glB,Snöröjd yta snöröjningsklass 3 - gyB,Soffa/bänk, fast - sB,Soffa/bänkbord, löst - sB,Strid sand - gyB,Säckställ - sB,Torg - gyB,Trappa - gyB,Trappa snöröjningsklass 3 - gyB,Trappa snöröjningsklass 6 - gyB,Trappväg snöröjningsklass 6 - gyB,Träbelagd yta - gyB,Trädbevuxen naturmark, skog - gyB,Vippgunga/gungbräda - sB,Växtdamm/dagvattendamm - gyB,Yta med annan funktion än park - gyB,Öppen naturmark - gyB,Övrig lekutrustning - sB,Övrig natursten - gyB
    Snöröjd sträcka snöröjningsklass 3 - glB -> LineOnLineOverlayer [LINE]
    Snöröjd sträcka snöröjningsklass 6 - glB -> LineOnLineOverlayer_2 [LINE]
    Snöröjd sträcka snöröjningsklass 6 - glB -> Junction_12
Note: SpatialFilter_3 : Filter
Junction_12
    -> Junction_13
LineCombiner
    ACCUM_ATTRS_NAME = Use Attributes From One Feature
    CLOSE = yes
    CONNECT_Z_MODE_LOOKUP = FIRST_WINS
    CONSIDER_NODE_ELEVATION_LOOKUP = NO
    DEAGGREGATE_GEOMETRY = Deaggregate
    JUNCTIONS_IGNORE_ATTRIBUTES = No
    LINES_AS_SEGMENTS = No
    NODED = END_NODED
    PRESERVE = no
    BREAK = no
    CONNECT_Z_MODE = First Wins
    CONSIDER_NODE_ELEVATION = no
    TOPOLOGY = End Noded
    LINE -> Junction_14
Note: SpatialFilter : Candidate
Junction_14
    -> Junction_15
Note: SpatialFilter_4 : Filter
Junction_10
    -> Junction_11
Note: Tester_16 : Passed
Junction_11
    -> SpatialFilter_4 [Filter]
Junction_2
    -> AttributeRemover_2
Note: ta bort oönskade attribut
AttributeRemover_2
    REMOVE_ATTRS = _bygglov_diarienummer_public,_clipped,_column,_geometry_name,_grupp,_matched_records,_overlaps,_overlaps1,_overlapsNY,_part_number,_related_suppliers,_row,_whereBaggis,absolutLagesosakerhetHojd,absolutLagesosakerhetPlan,ANL_NAMN,BREDD,CA_NAME,CTABLE,DIARIENR,DP_CTYPE,DP_DELETED,DP_MOD,DP_OCCURRENCE,DP_OTYPE,DP_OTYPE_NAME,DP_SIGN,DP_SUBTYPE,DP_SUBTYPE_NAME,FILL_COLOR,HUSNR,INM_LAGE,INM_LAGE_TEXT,INMATNINGSANV,KANTSTOD,KANTSTOD_TEXT,KOM_ID,KONSTRUERAD,KONSTRUERAD_TEXT,KRONRADIE,LANDMARKE,MARK,MATANVISNINGAR,metodIHojdTyp,metodIPlanTidsperiodFran,metodIPlanTidsperiodTill,metodIPlanTyp,OSKARP,OSKARP_TEXT,PROD_CLASS_ID,PROD_ELEV,PROD_PLANE,PRODUCT_NAME,RELATIV_HOJD,STADIUM,STAMDIAM,SVE_NAMN,SYMBOL,tidpunktForKontrollAvGeometri,tidpunktForLagesbestamning,TIDSPERIOD-UNDERLAG_GEOIDMODELL,TRADHOJD,TRADSORT,TRADSORT_NAMN,TRADTYP,TRADTYP_NAMN,UUID_BYGGNAD,VANSTER,VANSTER_TEXT,VARIANT_NAMN,VET_NAMN,VET_NAMN_NAMN,VARIANT
    -> AttributeFilter_2
AttributeFilter_2
    ATTR_NAME = 1_Temaklass
    ATTR_VALUES = <Empty>,<Missing>,<Null>,<Unfiltered>,Anläggning,Byggnad,Missing,Stor yta,Väg
    Anläggning -> FeatureColorSetter_2
    Byggnad -> FeatureColorSetter
    Missing -> FeatureColorSetter_4
    Stor yta -> FeatureColorSetter_3
    Väg -> Junction_3
Junction_3
    -> AttributeFilter_3
AttributeFilter_3
    ATTR_NAME = LOD2
    ATTR_VALUES = <Empty>,<Missing>,<Null>,<Unfiltered>,Cykelväg,GC-väg,Gångväg,Körbana,Separering
    <MISSING> -> Junction_4
    Cykelväg -> SpatialFilter_4 [Candidate]
    GC-väg -> Junction_4
    Gångväg -> SpatialFilter [Filter]
    Gångväg -> SpatialFilter_2 [Candidate]
    Körbana -> Tester_12
    Separering -> Junction_4
Note: Göra om cykelbana till track
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator
    FAILED -> Junction_4
Junction_4
    -> Tester_17
Tester_17
    BOOL_OP = AND
    TEST_CLAUSE:
      TEST @Value(1_Temaklass) = Väg
      TEST 4_Track ATTRIBUTE_IS_MISSING ""
    TEST_MODE = TEST
    PASSED -> Tester_18
    FAILED -> Junction_17
Tester_18
    BOOL_OP = AND
    TEST_CLAUSE:
      TEST @Value(LOD2) = Körbana
      TEST @Value(LOD3) != Ej Huvudled
    TEST_MODE = TEST
    PASSED -> Bufferer_2
    PASSED -> Bufferer_3
    PASSED -> Bufferer_4
    PASSED -> Junction_17
    FAILED -> AttributeFilter_5
Bufferer_2
    ANGLE = 22.5
    CAP_STYLE_LOOKUP = CAP_PROJECTING
    CORNER_STYLE_LOOKUP = JOIN_ARC
    MODE = AREA
    OFFSET = 10
    OFFSET_UNITS = NONE
    PRECISION = APPROX
    CAP_STYLE = Square
    CORNER_STYLE = Arc
    BUFFERED -> Clipper_5 [CLIPPER]
AttributeFilter_5
    ATTR_NAME = LOD2
    ATTR_VALUES = <Empty>,<Missing>,<Null>,<Unfiltered>,Cykelväg,GC-väg,Gångväg,Körbana,Separering
    <MISSING> -> Junction_16
    Cykelväg -> Clipper_8 [CANDIDATE]
    GC-väg -> Clipper_7 [CANDIDATE]
    Gångväg -> Clipper_5 [CANDIDATE]
    Körbana -> Junction_16
    Separering -> Junction_16
Junction_16
    -> Junction_5
Junction_17
    -> Junction_5
Bufferer_3
    ANGLE = 22.5
    CAP_STYLE_LOOKUP = CAP_PROJECTING
    CORNER_STYLE_LOOKUP = JOIN_ARC
    MODE = AREA
    OFFSET = 10
    OFFSET_UNITS = NONE
    PRECISION = APPROX
    CAP_STYLE = Square
    CORNER_STYLE = Arc
    BUFFERED -> Clipper_7 [CLIPPER]
Bufferer_4
    ANGLE = 22.5
    CAP_STYLE_LOOKUP = CAP_ARC
    CORNER_STYLE_LOOKUP = JOIN_ARC
    MODE = AREA
    OFFSET = 15
    OFFSET_UNITS = NONE
    PRECISION = APPROX
    CAP_STYLE = Arc
    CORNER_STYLE = Arc
    BUFFERED -> Clipper_8 [CLIPPER]
Junction_5
    -> NewFeatureType (writer FFS_5)
    -> NewFeatureType (writer FFS_9)
    -> NewFeatureType (writer FFS_14)

Bookmark: 4_AUX_YTOR_TESTOMRÅDE_KUNGSHOLMEN
NewFeatureType (reader FFS_13) [off]
    attributes: LOD1 varchar(9), DP_SUBTYPE_NAME buffer, LOD2 varchar(7), LOD3 varchar(5), ROUTE_ID varchar(38), Typ_512 varchar(23), GCM_t_502 varchar(37), Vagtr_474 varchar(10), _part_number uint64, _geometry_name buffer, _count int64, Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200),
      STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), INM_LAGE int32, LANDMARKE int32,
      VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32,
      _right_face uint32, _left_face uint32, _faces uint32, _creation_instance uint64, Added_line varchar(4)
    -> GeometryFilter_2

Bookmark: 4_AUX_YTOR_TESTOMRÅDE_KISTA
NewFeatureType (reader FFS_6) [off]
    attributes: LOD1 varchar(9), DP_SUBTYPE_NAME buffer, LOD2 varchar(7), LOD3 varchar(5), ROUTE_ID varchar(38), Typ_512 varchar(23), GCM_t_502 varchar(37), Vagtr_474 varchar(10), _part_number uint64, _geometry_name buffer, _count int64, Skymd varchar(2), 1_Temaklass varchar(7), 2_Klass varchar(7), 3_Subklass varchar(1), DP_OTYPE buffer, DP_OTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200),
      STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), INM_LAGE int32, LANDMARKE int32,
      VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32,
      _right_face uint32, _left_face uint32, _faces uint32, _creation_instance uint64, Added_line varchar(4)
    -> GeometryFilter_2

Bookmark: 4_AUX_YTOR_TRÄNINGSOMRÅDE_KISTA
NewFeatureType (reader FFS_3)
    attributes: BM_ANVD varchar(2), LOD1 varchar(9), DP_SUBTYPE_NAME buffer, LOD2 varchar(7), LOD3 varchar(5), ROUTE_ID varchar(38), Typ_512 varchar(23), GCM_t_502 varchar(37), Vagtr_474 varchar(10)
    -> AreaOnAreaOverlayer [AREA]

Bookmark: 2_BK_CLEAN_TRÄNINGSOMRÅDE_KISTA
NewFeatureType (reader FFS_1)
    attributes: DP_SUBTYPE_NAME buffer
    -> AttributeExposer

Bookmark: 2_BK_CLEAN_TESTOMRÅDE_KISTA
NewFeatureType (reader FFS_2) [off]
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> AttributeExposer

Bookmark: 2_BK_CLEAN_TESTOMRÅDE_KUNGSHOLMEN
NewFeatureType (reader FFS_12) [off]
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> AttributeExposer

Bookmark: Preprocessing av BK Clean
Note: Exposa vissa attribut
AttributeExposer
    ATTR_TABLE = 1_Temaklass,varchar(11),2_Klass,varchar(25),3_Subklass,varchar(27)
    -> AreaBuilder
Note: Skapa ytor
AreaBuilder
    ALLOW_CYCLES = No
    CHECK_CURVE_DIRECTION = No
    CONNECT_Z_MODE_LOOKUP = FIRST_WINS
    CONSIDER_NODE_ELEVATION_LOOKUP = NO
    DEAGGREGATE_INPUT = Deaggregate
    DONUT_CREATION = Yes
    DROP_HOLES = No
    LINES_AS_SEGMENTS = No
    POLY_ACCUM_ATTRS_NAME = Use Attributes From One Feature
    SNAPTYPE = NONE
    CONNECT_Z_MODE = First Wins
    CONSIDER_NODE_ELEVATION = no
    SNAPTYPE_PARAM = None
    AREA -> AttributeRemover
Note: Ta bort oönskade attribut
AttributeRemover
    REMOVE_ATTRS = DP_SUBTYPE_NAME
    -> Counter
Note: Skapa ID som används under dissolven
Counter
    CNT_ATTR = _count
    DOMAIN = counter
    SCOPE = Global
    START = 0
    -> AreaOnAreaOverlayer [AREA]

Bookmark: Tätning av de mergade BK clean och MERGE TY. Säkerställer att inga små sliver ytor och rester kvarstår
Note: Dissolver enligt counter (ID). Dissolverar enligt BK
Dissolver
    ACCUM_INPUT_ATTRS = Use Attributes From One Feature
    CLEANING_TOLERANCE_LOOKUP = AUTO
    CONNECT_Z_MODE_LOOKUP = FIRST_WINS
    DEAGGREGATE_INPUT = Yes
    GROUP_BY = _count
    CLEANING_TOLERANCE = Automatic
    CONNECT_Z_MODE = First Wins
    AREA -> Tester_3
Note: Hittar små restytor
Tester_3
    BOOL_OP = OR
    TEST_CLAUSE = TEST @Area() < 1
    TEST_MODE = TEST
    FAILED -> Snapper
Note: Snappar ihop ytorna för att städa glappen lämnade av restytorna
Snapper
    CLEANING_TOLERANCE_LOOKUP = AUTO
    SNAPTYPE = ALL
    TOLERANCE = 0.5
    CLEANING_TOLERANCE = Automatic
    SNAPPED -> Tester_4
    UNTOUCHED -> Tester_4
Note: Hittar små restytor
Tester_4
    BOOL_OP = OR
    TEST_CLAUSE = TEST @Area() < 1
    TEST_MODE = TEST
    FAILED -> AreaGapAndOverlapCleaner
Note: Städar glapp som kvarstår från restytorna
AreaGapAndOverlapCleaner
    CLEANING_TOLERANCE_LOOKUP = AUTO
    CONNECT_Z_MODE_LOOKUP = FIRST_WINS
    DEAGGREGATE_INPUT = YES
    FILL_ALL_GAPS = No
    MEASURE_TYPE_LOOKUP = CONTINUOUS
    MISSING_VAL_MODE_LOOKUP = COMPUTE_NANS
    REPAIR = LongestBoundary
    CLEANING_TOLERANCE = Automatic
    CONNECT_Z_MODE = First Wins
    MEASURE_TYPE = Continuous
    MISSING_VAL_MODE = Compute
    REPAIR_METHOD = Longest Boundary
    REPAIRED -> Deaggregator
Note: Säkerställ individuella ytor
Deaggregator
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> Tester

Bookmark: 1_NEW_ATTRIBUTES_KISTA
NewFeatureType (reader FFS_4)
    attributes: 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer,
      DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32,
      VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4)
    -> Clipper [CANDIDATE]

Bookmark: 1_NEW_ATTRIBUTES_KUNGSHOLMEN
NewFeatureType (reader FFS_10) [off]
    attributes: 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer,
      DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32,
      VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4)
    -> Clipper [CANDIDATE]

Bookmark: Kvartersdata
kvarter_yta (reader OGCGEOPACKAGE_2)
    attributes: objekttypnr int, objekttyp text, subtypnr int, subtyp text, kvartersnamn text, lagesosakerhet_plan text, objektid int, tid_modifierad int, id int,PrimaryKey
    -> Clipper_3 [CANDIDATE]

Bookmark: Ram Träningsområde Kista
Default (reader DGNV8_1)
    -> Clipper [CLIPPER]
    -> Clipper_3 [CLIPPER]
    -> Clipper_4 [CLIPPER]

Bookmark: Ram Testområde Kista
VERIF (reader FFS_7) [off]
    attributes: _creation_instance uint64
    -> Clipper_3 [CLIPPER]
    -> Clipper [CLIPPER]
    -> Clipper_4 [CLIPPER]

Bookmark: Ram Testområde Kungsholmen
NewFeatureType (reader FFS_11) [off]
    attributes: _creation_instance uint64
    -> Clipper_3 [CLIPPER]
    -> Clipper_4 [CLIPPER]
    -> Clipper [CLIPPER]

Bookmark: Preprocesing för att ta fram byggnader och anläggningar
Note: Klipp mot urklippet av området
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Tester_5
    INSIDE -> GeometryCoercer
Note: Tester_5 [Tester] / Test Clauses: LogicLeft ValueOperatorRight Value@Value(4_Slask)=TrueOR@Value(CTYPE_NAME)=glBFotoAdvanced: / Preserve Feature Order: Per Output Port
Tester_5
    BOOL_OP = OR
    TEST_CLAUSE:
      TEST @Value(4_Slask) = True
      TEST @Value(CTYPE_NAME) = glBFoto
    TEST_MODE = TEST
    FAILED -> GeometryFilter
Note: Säkerställ rätt geometri
GeometryFilter
    FILTER_MODE = SIMPLE
    FILTER_MULTI = FILTER_TYPES]"Point Line Area"]FME_CONTROLLER_QUERY_FILE]]FME_CONTROLLER_CHOICE]Simple
    Curve -> LineOnAreaOverlayer [LINE]
    Area -> LineOnAreaOverlayer [AREA]
Note: Få med interna strukturer av ytorna
LineOnAreaOverlayer
    CLEANING_TOLERANCE_LOOKUP = AUTO
    DEAGGREGATE_INPUT = Yes
    OVERLAY_TYPE = AREA_ON_LINE
    OV_ATTR = _overlaps
    CLEANING_TOLERANCE = Automatic
    AREA -> AttributeFilter
AttributeFilter
    ATTR_NAME = 1_Temaklass
    ATTR_VALUES = <Empty>,<Missing>,<Null>,<Unfiltered>,Anläggning,Byggnad,Natur,Trappa,Väg
    Anläggning -> Junction_8
    Byggnad -> Tester_7

Bookmark: Attribut information - Byggnader
Note: Filtrera bort regnskydd
Tester_7
    BOOL_OP = OR
    TEST_CLAUSE = TEST @Value(3_Subklass) != Regnskydd
    TEST_MODE = TEST
    PASSED -> PointOnAreaOverlayer_2 [AREA]
    PASSED -> Tester_8
Note: Test för att filtrera för små ytor som inte kan negativt buffras
Tester_8
    BOOL_OP = OR
    TEST_CLAUSE = TEST @Area() < 8
    TEST_MODE = TEST
    PASSED -> Clipper_2 [CLIPPER]
    FAILED -> Bufferer
Note: Negativ buffer
Bufferer
    ANGLE = 22.5
    CAP_STYLE_LOOKUP = CAP_ARC
    CORNER_STYLE_LOOKUP = JOIN_ARC
    MODE = AREA
    OFFSET = -0.5
    OFFSET_UNITS = NONE
    PRECISION = APPROX
    CAP_STYLE = Arc
    CORNER_STYLE = Arc
    BUFFERED -> Clipper_2 [CLIPPER]
Note: Skapa grid för att overlaya mot byggnaderna
2DGridCreator
    BBOX_TYPE = GRID_CORNERS
    COL_ATTR = _column
    COORDSYS = SWEREF-99-18-00
    GRID_ORIGIN = BOTTOM_LEFT
    NUMCOLS = 2500
    NUMROWS = 2500
    ROW_ATTR = _row
    STARTINGX = 146364.2648
    STARTINGY = 6587743.3348
    XINC = 1.5
    YINC = 1.5
    GRID_TYPE = Points (Corners)
    STARTINGCORNER = Lower Left
    CREATED -> Reprojector
Note: Byt koordinatsystem
Reprojector
    DEST = SWEREF-99-18-00
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper_2 [CANDIDATE]
Note: Klipp gridet mot byggnaderna
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> PointOnAreaOverlayer_2 [POINT]
Note: Overlaya byggnaderna och punkterna
PointOnAreaOverlayer_2
    ATTR_ACCUM_MODE = Merge Incoming
    ATTR_CONFLICT_RES_LOOKUP = ORIGINAL_IF_CONFLICT
    DEAGGREGATE_INPUT = Yes
    OV_ATTR = _overlaps
    POLYS_FIRST = NO
    ATTR_CONFLICT_RES = Use Original
    POINT -> PointOnAreaOverlayer [POINT]
PointOnAreaOverlayer
    ATTR_ACCUM_MODE = Merge Incoming
    ATTR_CONFLICT_RES_LOOKUP = INCOMING_IF_CONFLICT
    DEAGGREGATE_INPUT = Yes
    OV_ATTR = _overlapsNY
    POLYS_FIRST = NO
    ATTR_CONFLICT_RES = Use Incoming
    AREA -> Tester_6
Note: Tester_6 [Tester] / Test Clauses: Left ValueOperatorRight Value@Value(_overlapsNY)>0Advanced: / Preserve Feature Order: Per Output Port
Tester_6
    BOOL_OP = OR
    TEST_CLAUSE = TEST @Value(_overlapsNY) > 0
    TEST_MODE = TEST
    PASSED -> Junction_2
    FAILED -> Tester_9

Bookmark: Attribut information - Anläggning
Note: AttributeFilter : Anläggning
Junction_9
    -> CenterPointReplacer
Note: Ersätt geometrin med en punkt
CenterPointReplacer
    POINTTYPE = INSIDE
    POINT -> PointOnAreaOverlayer_3 [POINT]
PointOnAreaOverlayer_3
    ATTR_ACCUM_MODE = Merge Incoming
    ATTR_CONFLICT_RES_LOOKUP = INCOMING_IF_CONFLICT
    DEAGGREGATE_INPUT = Yes
    OV_ATTR = _overlaps1
    POLYS_FIRST = NO
    ATTR_CONFLICT_RES = Use Incoming
    AREA -> Tester_10
Note: Test för overlaps
Tester_10
    BOOL_OP = OR
    TEST_CLAUSE = TEST @Value(_overlaps1) > 0
    TEST_MODE = TEST
    PASSED -> Junction_2
    FAILED -> AttributeManager_4
AttributeManager_4
    ATTR_TABLE:
      SET_TO 1_Temaklass (varchar(7)) = Missing
      SET_TO 2_Klass (varchar(7)) = Missing
      SET_TO 3_Subklass (varchar(7)) = Missing
    -> Junction_2

Bookmark: Göra parkering/infart till track
Note: Clipper_3 : Inside
Junction_7
    -> Clipper_6 [CLIPPER]
Note: AttributeFilter_4 : Snöröjd sträcka snöröjningsklass 6 - glB
Junction_13
    -> SpatialFilter_3 [Filter]
Note: tester för infart/parkering
Tester_12
    BOOL_OP = OR
    TEST_CLAUSE = TEST @Value(LOD3) = Ej Huvudled
    TEST_MODE = TEST
    PASSED -> Clipper_6 [CANDIDATE]
    FAILED -> Junction_4
Clipper_6
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Dissolver_3
    OUTSIDE -> Deaggregator_4
Deaggregator_4
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> SpatialFilter_3 [Candidate]
Note: Kolla överlapp med parkdata
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator
    FAILED -> Dissolver_3
Dissolver_3
    ACCUM_INPUT_ATTRS = Use Attributes From One Feature
    CLEANING_TOLERANCE_LOOKUP = AUTO
    CONNECT_Z_MODE_LOOKUP = FIRST_WINS
    DEAGGREGATE_INPUT = Yes
    GROUP_BY = _count
    CLEANING_TOLERANCE = Automatic
    CONNECT_Z_MODE = First Wins
    AREA -> Junction_4

Bookmark: Parkdata
symbol (reader OGCGEOPACKAGE_4)
    attributes: dp_otype int, dp_oid int, dp_ctype int, dp_subtype int, dp_occ int, dp_lock int, dp_deleted int, dp_state int, dp_dsp_flg int, sub_c_type text, font text, font_id text, rotation double, height double, width double, fid int,PrimaryKey
    -> Clipper_4 [CANDIDATE]

Bookmark: Borttagning av för korta linjer
LineOnLineOverlayer
    ATTRS_ACCUM_MODE = Use Attributes From One Feature
    CLEANING_TOLERANCE_LOOKUP = AUTO
    DEAGGREGATE_INPUT = Yes
    GENERATE_LIST_DROP = NO
    OV_ATTR = _overlaps
    SEPARATE_COLLINEAR_SEGMENTS = No
    CLEANING_TOLERANCE = Automatic
    LINE -> Tester_13
Tester_13
    BOOL_OP = OR
    TEST_CLAUSE = TEST @Value(sub_c_type) = Snöröjd sträcka snöröjningsklass 3 - glB
    TEST_MODE = TEST
    PASSED -> LengthCalculator
LengthCalculator
    DIM = 2
    LEN_ATTR = _length
    MULT = 1
    -> Tester_14
Tester_14
    BOOL_OP = OR
    TEST_CLAUSE = TEST @Value(_length) < 1
    TEST_MODE = TEST
    FAILED -> LineCombiner

Bookmark: Göra om gångbana till track
Note: LineCombiner : Line
Junction_15
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator
    FAILED -> Junction_4

Bookmark: Borttagning av för korta linjer
LineOnLineOverlayer_2
    ATTRS_ACCUM_MODE = Use Attributes From One Feature
    CLEANING_TOLERANCE_LOOKUP = AUTO
    DEAGGREGATE_INPUT = Yes
    GENERATE_LIST_DROP = NO
    OV_ATTR = _overlaps
    SEPARATE_COLLINEAR_SEGMENTS = No
    CLEANING_TOLERANCE = Automatic
    LINE -> Tester_15
Tester_15
    BOOL_OP = OR
    TEST_CLAUSE = TEST @Value(sub_c_type) = Snöröjd sträcka snöröjningsklass 6 - glB
    TEST_MODE = TEST
    PASSED -> LengthCalculator_2
LengthCalculator_2
    DIM = 2
    LEN_ATTR = _length
    MULT = 1
    -> Tester_16
Tester_16
    BOOL_OP = OR
    TEST_CLAUSE = TEST @Value(_length) > 23.5
    TEST_MODE = TEST
    PASSED -> Junction_10

Bookmark: Attribut information - Missing
Tester_9
    BOOL_OP = OR
    TEST_CLAUSE = TEST @Value(1_Temaklass) = Byggnad
    TEST_MODE = TEST
    PASSED -> AttributeManager_3
    FAILED -> Junction
AttributeManager_3
    ATTR_TABLE:
      SET_TO 1_Temaklass (varchar(7)) = Missing
      SET_TO 2_Klass (varchar(7)) = Missing
      SET_TO 3_Subklass (varchar(7)) = Missing
    -> Junction
Junction
    -> PointOnAreaOverlayer_3 [AREA]

Bookmark: Färgsättning
FeatureColorSetter_2
    ALGORITHM = MANUAL
    COLOR = 0.666667,0,0.498039
    FILL_COLOR = 0.666667,0,0.498039
    MODE = Fixed
    COLORED -> Junction_3
FeatureColorSetter
    ALGORITHM = MANUAL
    COLOR = 0.666667,0.666667,0
    FILL_COLOR = 0.666667,0.666667,0
    MODE = Fixed
    COLORED -> Junction_3
FeatureColorSetter_3
    ALGORITHM = MANUAL
    COLOR = 0.333333,0.666667,0.498039
    FILL_COLOR = 0.333333,0.666667,0.498039
    MODE = Fixed
    COLORED -> Junction_3
FeatureColorSetter_4
    ALGORITHM = MANUAL
    COLOR = 0.952941,0.952941,0.952941
    FILL_COLOR = 0.952941,0.952941,0.952941
    MODE = Fixed
    COLORED -> Junction_3

Bookmark: Skapa attribut för track
AttributeCreator
    ATTR_TABLE = SET_TO 4_Track (varchar(5)) = Track
    -> FeatureColorSetter_6
FeatureColorSetter_6
    ALGORITHM = MANUAL
    COLOR = 1,0.666667,1
    FILL_COLOR = 1,0.666667,1
    MODE = Fixed
    COLORED -> Junction_4

Bookmark: Gånväg till track
Clipper_5
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Dissolver_2
    OUTSIDE -> Deaggregator_2
Deaggregator_2
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> Tester_19
Tester_19
    BOOL_OP = OR
    TEST_CLAUSE = TEST @Area() < 10
    TEST_MODE = TEST
    PASSED -> Dissolver_6
    FAILED -> AttributeCreator_2
Dissolver_6
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> Tester_23
Tester_23
    BOOL_OP = OR
    TEST_CLAUSE = TEST @Area() < 5
    TEST_MODE = TEST
    PASSED -> Tester_24
    FAILED -> AttributeCreator_2
Tester_24
    BOOL_OP = OR
    TEST_CLAUSE = TEST @Value(DP_OID) = 59019941
    TEST_MODE = TEST
    PASSED -> AttributeCreator_2
    FAILED -> Dissolver_2
Dissolver_2
    ACCUM_INPUT_ATTRS = Use Attributes From One Feature
    CLEANING_TOLERANCE_LOOKUP = AUTO
    CONNECT_Z_MODE_LOOKUP = FIRST_WINS
    DEAGGREGATE_INPUT = Yes
    GROUP_BY = _count
    CLEANING_TOLERANCE = Automatic
    CONNECT_Z_MODE = First Wins
    AREA -> Junction_5

Bookmark: GC-väg till track
Note: Klipp mot buffrad körbana
Clipper_7
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Tester_20
    OUTSIDE -> Dissolver_4
Tester_20
    BOOL_OP = OR
    TEST_CLAUSE = TEST @Area() < 20
    TEST_MODE = TEST
    PASSED -> Dissolver_4
    FAILED -> Junction_5
Dissolver_4
    ACCUM_INPUT_ATTRS = Use Attributes From One Feature
    CLEANING_TOLERANCE_LOOKUP = AUTO
    CONNECT_Z_MODE_LOOKUP = FIRST_WINS
    DEAGGREGATE_INPUT = Yes
    GROUP_BY = _count
    CLEANING_TOLERANCE = Automatic
    CONNECT_Z_MODE = First Wins
    AREA -> Tester_21
Tester_21
    BOOL_OP = OR
    TEST_CLAUSE = TEST @Area() < 400
    TEST_MODE = TEST
    PASSED -> Junction_5
    FAILED -> AttributeCreator_2

Bookmark: Cykelväg till track
Note: Klipp mot buffrad körbana
Clipper_8
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Dissolver_5
    OUTSIDE -> Deaggregator_3
Deaggregator_3
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> Tester_22
Tester_22
    BOOL_OP = OR
    TEST_CLAUSE = TEST @Area() < 130
    TEST_MODE = TEST
    PASSED -> Dissolver_5
    FAILED -> AttributeCreator_2
Dissolver_5
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> Junction_5

Bookmark: Skapa attribut för track
AttributeCreator_2
    ATTR_TABLE = SET_TO 4_Track (varchar(5)) = Track
    -> FeatureColorSetter_5
FeatureColorSetter_5
    ALGORITHM = MANUAL
    COLOR = 1,0.666667,1
    FILL_COLOR = 1,0.666667,1
    MODE = Fixed
    COLORED -> Junction_5

Bookmark: 5_MERGE_YTOR_TRÄNINGSOMRÅDE_KISTA
NewFeatureType (writer FFS_5) [off]
    attributes: BM_ANVD varchar(2), LOD1 varchar(9), LOD2 varchar(7), LOD3 varchar(5), ROUTE_ID varchar(38), Typ_512 varchar(23), GCM_t_502 varchar(37), Vagtr_474 varchar(10), 1_Temaklass varchar(7), 2_Klass varchar(7), 3_Subklass varchar(1), _count int64, Skymd varchar(2), DP_OID int64, CTYPE_NAME buffer, MARK_TEXT varchar(40), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4),
      _clipped char(3), _part_number uint64, _geometry_name buffer, 4_Track varchar(5), DP_OTYPE buffer, DP_OTYPE_NAME buffer, DP_SUBTYPE_NAME buffer, DP_CTYPE buffer, SYMBOL buffer, PRODUCT_NAME buffer, DP_MOD buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer,
      DP_DELETED buffer, TIDSPERIOD-UNDERLAG_GEOIDMODELL varchar(40), _grupp buffer, KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100),
      TRADSORT_NAMN varchar(100), TRADTYP_NAMN varchar(100), KRONRADIE real64, STAMDIAM real64, TRADHOJD real64, TRADSORT int32, TRADTYP int32, VET_NAMN int32, SVE_NAMN varchar(50), dp_otype int64, dp_oid int64, dp_ctype int64, dp_subtype int64, dp_occ int64, dp_lock int64, dp_deleted int64, dp_state int64, dp_dsp_flg int64, sub_c_type buffer, font buffer, font_id buffer, rotation real64, height real64, width real64, fid int64, _overlaps uint32, _length real64, _predicate buffer

Bookmark: 5_MERGE_YTOR_TESTOMRÅDE_KISTA
NewFeatureType (writer FFS_9) [off]
    attributes: BM_ANVD varchar(2), LOD1 varchar(9), LOD2 varchar(7), LOD3 varchar(5), ROUTE_ID varchar(38), Typ_512 varchar(23), GCM_t_502 varchar(37), Vagtr_474 varchar(10), 1_Temaklass varchar(7), 2_Klass varchar(7), 3_Subklass varchar(1), _count int64, Skymd varchar(2), DP_OID int64, CTYPE_NAME buffer, MARK_TEXT varchar(40), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4),
      _clipped char(3), _part_number uint64, _geometry_name buffer, 4_Track varchar(5), DP_OTYPE buffer, DP_OTYPE_NAME buffer, DP_SUBTYPE_NAME buffer, DP_CTYPE buffer, SYMBOL buffer, PRODUCT_NAME buffer, DP_MOD buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer,
      DP_DELETED buffer, TIDSPERIOD-UNDERLAG_GEOIDMODELL varchar(40), _grupp buffer, KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100),
      TRADSORT_NAMN varchar(100), TRADTYP_NAMN varchar(100), KRONRADIE real64, STAMDIAM real64, TRADHOJD real64, TRADSORT int32, TRADTYP int32, VET_NAMN int32, SVE_NAMN varchar(50), dp_otype int64, dp_oid int64, dp_ctype int64, dp_subtype int64, dp_occ int64, dp_lock int64, dp_deleted int64, dp_state int64, dp_dsp_flg int64, sub_c_type buffer, font buffer, font_id buffer, rotation real64, height real64, width real64, fid int64, _overlaps uint32, _length real64, _predicate buffer

Bookmark: 5_MERGE_YTOR_TESTOMRÅDE_KUNGSHOLMEN
NewFeatureType (writer FFS_14) [off]
    attributes: BM_ANVD varchar(2), LOD1 varchar(9), LOD2 varchar(7), LOD3 varchar(5), ROUTE_ID varchar(38), Typ_512 varchar(23), GCM_t_502 varchar(37), Vagtr_474 varchar(10), 1_Temaklass varchar(7), 2_Klass varchar(7), 3_Subklass varchar(1), _count int64, Skymd varchar(2), DP_OID int64, CTYPE_NAME buffer, MARK_TEXT varchar(40), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4),
      _clipped char(3), _part_number uint64, _geometry_name buffer, 4_Track varchar(5), DP_OTYPE buffer, DP_OTYPE_NAME buffer, DP_SUBTYPE_NAME buffer, DP_CTYPE buffer, SYMBOL buffer, PRODUCT_NAME buffer, DP_MOD buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer,
      DP_DELETED buffer, TIDSPERIOD-UNDERLAG_GEOIDMODELL varchar(40), _grupp buffer, KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100),
      TRADSORT_NAMN varchar(100), TRADTYP_NAMN varchar(100), KRONRADIE real64, STAMDIAM real64, TRADHOJD real64, TRADSORT int32, TRADTYP int32, VET_NAMN int32, SVE_NAMN varchar(50), dp_otype int64, dp_oid int64, dp_ctype int64, dp_subtype int64, dp_occ int64, dp_lock int64, dp_deleted int64, dp_state int64, dp_dsp_flg int64, sub_c_type buffer, font buffer, font_id buffer, rotation real64, height real64, width real64, fid int64, _overlaps uint32, _length real64, _predicate buffer
