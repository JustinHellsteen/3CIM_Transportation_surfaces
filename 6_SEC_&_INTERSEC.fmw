FME workspace 6_SEC_&_INTERSEC.fmw

Parameters:
- SourceDataset_FILEGDB = C:\Users\ai31986\HCP\Examensarbete\Data\NVDB\Trafikverket_NVDB_väg-homogeniserade_2024-04-19_JUSTERAD-LAGE.gdb   # File Geodatabase
- SourceDataset_DGNV8 = C:\Users\ai31986\HCP\Examensarbete\Data\Ramar\Urklipp runt Kistaäng.dgn   # Source Bentley MicroStation Design File(s)
- SourceDataset_FFS_3 = C:\Users\ai31986\HCP\Examensarbete\FME Projekt workspaces\5_SAMTLIGA_YTOR\OUTPUT\5_SAMTLIGA_YTOR.ffs   # Source FME Feature Store (FFS) File(s)
- SourceDataset_FFS = C:\Users\ai31986\HCP\Examensarbete\FME Projekt workspaces\2_BK_CLEAN\OUTPUT\2_BK_CLEAN.ffs   # Source FME Feature Store (FFS) File(s)
- DestDataset_FFS_2 = $(FME_MF_DIR)OUTPUT\6_INTERSECTIONS_LOD2.ffs   # Destination FME Feature Store (FFS) File
- DestDataset_FFS = $(FME_MF_DIR)OUTPUT\6_INTERSECTIONS_LOD1.ffs   # Destination FME Feature Store (FFS) File
- SourceDataset_DGNV8_3 = C:\Users\ai31986\HCP\Examensarbete\Data\Korsningar\Stockholm_vagkorsning_ytor_enligt TUM LOD1.dgn   # Source Bentley MicroStation Design File(s)
- FEATURE_TYPES =
- SourceDataset_FFS_4 = C:\Users\ai31986\HCP\Examensarbete\FME Projekt workspaces\2_BK_CLEAN\OUTPUT\VERIF_2_BK_CLEAN.ffs   # Source FME Feature Store (FFS) File(s)
- SourceDataset_FFS_9 = C:\Users\ai31986\HCP\Examensarbete\Data\Ramar\VERIF.ffs   # Source FME Feature Store (FFS) File(s)
- SourceDataset_FFS_8 = C:\Users\ai31986\HCP\Examensarbete\FME Projekt workspaces\5_SAMTLIGA_YTOR\OUTPUT\VERIF_5_SAMTLIGA_YTOR.ffs   # Source FME Feature Store (FFS) File(s)
- DestDataset_FFS_6 = $(FME_MF_DIR)OUTPUT\VERI_6_INTERSECTIONS_LOD2.ffs   # Destination FME Feature Store (FFS) File
- SourceDataset_FFS_13 = C:\Users\ai31986\HCP\Examensarbete\Data\Ramar\RAM_KUNGSHOLMEN.ffs   # Source FME Feature Store (FFS) File(s)
- SourceDataset_FFS_15 = C:\Users\ai31986\HCP\Examensarbete\FME Projekt workspaces\2_BK_CLEAN\OUTPUT\2_BK_CLEAN_KUNGSHOLMEN.ffs   # Source FME Feature Store (FFS) File(s)
- SourceDataset_FFS_14 = C:\Users\ai31986\HCP\Examensarbete\FME Projekt workspaces\5_SAMTLIGA_YTOR\OUTPUT\5_SAMTLIGA_YTOR_KUNGSHOLMEN.ffs   # Source FME Feature Store (FFS) File(s)
- DestDataset_FFS_7 = $(FME_MF_DIR)OUTPUT\6_INTERSECTIONS_KUNGSHOLMEN_LOD2.ffs   # Destination FME Feature Store (FFS) File

Readers:
- FILEGDB_1: FILEGDB from $(SourceDataset_FILEGDB) in SWEREF-99-TM
- DGNV8_1: DGNV8 from $(SourceDataset_DGNV8) in SWEREF-99-18-00
- FFS_2: FFS from $(SourceDataset_FFS_3) in SWEREF-99-18-00
- FFS_1: FFS from $(SourceDataset_FFS) in SWEREF-99-18-00
- DGNV8_2: DGNV8 from $(SourceDataset_DGNV8_3) in SWEREF-99-18-00
- FFS_5: FFS from $(SourceDataset_FFS_4) in SWEREF-99-18-00
- FFS_6: FFS from $(SourceDataset_FFS_9) in SWEREF-99-18-00
- FFS_7: FFS from $(SourceDataset_FFS_8) in SWEREF-99-18-00
- FFS_10: FFS from $(SourceDataset_FFS_13) in SWEREF-99-18-00
- FFS_11: FFS from $(SourceDataset_FFS_15) in SWEREF-99-18-00
- FFS_12: FFS from $(SourceDataset_FFS_14) in SWEREF-99-18-00

Writers:
- FFS_3: FFS to $(DestDataset_FFS) in SWEREF-99-18-00
- FFS_4: FFS to $(DestDataset_FFS_2) in SWEREF-99-18-00
- FFS_9: FFS to $(DestDataset_FFS_6)
- FFS_13: FFS to $(DestDataset_FFS_7) in SWEREF-99-18-00

Junction_10
    -> Clipper_4 [CLIPPER]
    -> Clipper [CLIPPER]
Junction_9
    -> LineOnLineOverlayer [LINE]
Note: Filter för NVDB-länkar
AttributeFilter_2
    ATTR_NAME = GCM_t_502
    ATTR_VALUES = <Empty>,<Missing>,<Null>,<Unfiltered>,Annan cykelbar förbindelse,Cykelbana, påbjuden,Cykelpassage och övergångsställe,FME_NULL_VALUE,Gatupassage utan utmärkning,Gång- och cykelbana,Gång- och cykelbana, uppdelad,Gångbana,Torg/Öppen yta,Trappa,Övergångsställe
    Annan cykelbar förbindelse -> Junction_5
    Cykelbana, påbjuden -> Junction_5
    Gatupassage utan utmärkning -> Junction_5
    Gång- och cykelbana -> Junction_5
    Gång- och cykelbana, uppdelad -> Junction_5
    Gångbana -> Junction_5
    Torg/Öppen yta -> Junction_5
    Trappa -> Junction_5
Junction_5
Note: Filter för nvdb-LÄNKAR
AttributeFilter
    ATTR_NAME = Typ_512
    ATTR_VALUES = <Empty>,<Missing>,<Null>,<Unfiltered>,FME_NULL_VALUE,Huvudgata,Infartsväg/Utfartsväg,Kvartersväg,Lokalgata liten,Lokalgata stor,Parkeringsområdesväg
    Huvudgata -> Intersector
    Lokalgata liten -> Intersector
    Lokalgata stor -> Intersector
Note: LineExtender : Stretched
Junction_8
    -> LineOnAreaOverlayer_2 [LINE]
Note: Hitta linjesegmenten innanför buffern
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Densifier
Note: Ta bort slutnoder och då även end-caps för voronoiytorna
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> LineOnAreaOverlayer [AREA]
AttributeExposer
    ATTR_TABLE = 4_Track,
    -> Counter
Note: Tilldela varje feature ett "ID" count
Counter
    CNT_ATTR = _count
    DOMAIN = counter
    SCOPE = Global
    START = 0
    -> GeometryCoercer
    -> Clipper_3 [CANDIDATE]
    -> Junction
Note: Clipper_5 : Candidate
Junction
    -> Junction_2
Note: Counter : Output
Junction_2
    -> Clipper_5 [CANDIDATE]
    -> Clipper_6 [CLIPPER]
    -> Clipper_7 [CANDIDATE]
GeometryCoercer
    GQUERY:
      for $geom in //geometry
      where $geom/count(parent::geometry) = 0
      return number($geom/@fme_id)
    KIND = fme_line
    COERCED -> LineOnAreaOverlayer [LINE]
Clipper_6
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Clipper_5 [CLIPPER]
Clipper_5
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Tester_6
Clipper_7
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Deaggregator
    OUTSIDE -> LineOnAreaOverlayer_2 [AREA]
Note: Få in en linje
LineOnAreaOverlayer_2
    CLEANING_TOLERANCE_LOOKUP = AUTO
    DEAGGREGATE_INPUT = Yes
    OVERLAY_TYPE = AREA_ON_LINE
    OV_ATTR = _overlaps
    CLEANING_TOLERANCE = Automatic
    LINE -> LineOnAreaOverlayer_3 [LINE]
    AREA -> Deaggregator_2
Junction_6
    -> NewFeatureType (writer FFS_3)
Junction_4
    -> Deaggregator_3
Deaggregator_3
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> NewFeatureType (writer FFS_4)
    DEAGGREGATED -> NewFeatureType (writer FFS_9)
    DEAGGREGATED -> NewFeatureType (writer FFS_13)

Bookmark: NVDB-länkar
TNE_FT_VAGDATA (reader FILEGDB_1)
    attributes: ROUTE_ID text(38), FROM_MEASURE double, TO_MEASURE double, Korfa_524 int, F_ATK_Matplats smallint, B_ATK_Matplats smallint, F_Avser_28 text(3), B_Avser_28 text(3), F_Hogst_24 double, B_Hogst_24 double, Hogst_36 double, Hogst_46 double, Hogst_55_30 double, Typ_a_55_29 text(16), Ident_191 text(3000), Konst_190 text(23), Langd_192 double, Namn_193 text(3000), Brunn___Slamsugning smallint, L_Mater_301 text(15), R_Mater_301 text(15), Barig_64 text(25), Barig_504 text(25), C_Rekbilvagcykeltrafik smallint, F_Cirkulationsplats smallint, B_Cirkulationsplats smallint, entre_380 text(36), drift_2 text(34), LageF_83 text(42), TypAv_82 text(59),
      Framk_161 text(47), Klass_181 text(1), FPV_k_309 text(39), Funktionellt_priovagnat smallint, F_ForbjudenFardriktning smallint, B_ForbjudenFardriktning smallint, F_ForbudTrafik smallint, B_ForbudTrafik smallint, F_Beskr_454 text(3000), B_Beskr_454 text(3000), Namn_130 text(3000), Typ_512 text(23), GCM_belyst smallint, GCM_passage smallint, Passa_85 text(93), Trafi_86 text(22), L_Separ_500 text(13), R_Separ_500 text(13), GCM_t_502 text(37), L_Gagata smallint, R_Gagata smallint, L_Gangfartsomrade smallint, R_Gangfartsomrade smallint, F_Hogst_225 text(10), B_Hogst_225 text(10), Hallplats smallint, Plank_92 text(3000), F_Korfa_517 text(9), B_Korfa_517 text(9), mittr_10 text(8),
      Motortrafikled smallint, Motorvag smallint, Provisorisk_vag smallint, L_P_ficka smallint, R_P_ficka smallint, M_P_ficka smallint, Slitl_152 text(6), TattbebyggtOmrade smallint, Tillg_169 text(1), Under_397 text(48), L_VVIS smallint, R_VVIS smallint, slitl_25 text(15), Bredd_156 double, Hinde_72 text(39), Passe_73 double, Vagha_7 text(3000), Vagha_6 text(8), Forva_9 text(22), Avvik_540 text(8), Kateg_380 text(17), Europ_16 smallint, Huvud_13_1 int, Lanst_15 int, Under_14 int, Vagtr_474 text(10), korfa_52 text(17), vagty_41 text(24), Typ_369 text(23), Namn_132 text(3000),
      Namns_133 text(8), Kommu_141 text(3000), Vagkl_564 text(1), Vagnummer_ROLE text(11), OBJECTID objectid, SHAPE_Length double
    -> Reprojector

Bookmark: Förarbete med vägdata
Note: Fixa koordinatsystem
Reprojector
    DEST = SWEREF-99-18-00
    INTERPOLATION_TYPE = ,NearestNeighbor
    RASTER_CELL_SIZE_LOOKUP = ,PreserveCells
    RASTER_TOLERANCE = 0.0
    SOURCE = SWEREF-99-TM
    INTERPOLATION_TYPE_NAME = Nearest Neighbor
    RASTER_CELL_SIZE = Preserve Cells
    REPROJECTED -> Clipper [CANDIDATE]
Note: Klipp länkarna mot ramen
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> AttributeRemover
Note: Rensa attribut
AttributeRemover
    REMOVE_ATTRS = _clipped,Avvik_540,B_ATK_Matplats,B_Avser_28,B_Beskr_454,B_Cirkulationsplats,B_ForbjudenFardriktning,B_ForbudTrafik,B_Hogst_24,B_Hogst_225,B_Korfa_517,Barig_64,Barig_504,Bredd_156,Brunn___Slamsugning,C_Rekbilvagcykeltrafik,drift_2,entre_380,Europ_16,F_ATK_Matplats,F_Avser_28,F_Beskr_454,F_Cirkulationsplats,F_ForbjudenFardriktning,F_ForbudTrafik,F_Hogst_24,F_Hogst_225,F_Korfa_517,Forva_9,FPV_k_309,Framk_161,FROM_MEASURE,Funktionellt_priovagnat,GCM_belyst,GCM_passage,Hallplats,Hinde_72,Hogst_36,Hogst_46,Hogst_55_30,Huvud_13_1,Ident_191,Kateg_380,Klass_181,Kommu_141,korfa_52,Korfa_524,L_Gagata,L_Gangfartsomrade,L_Mater_301,L_P_ficka,L_Separ_500,L_VVIS,LageF_83,Langd_192,Lanst_15,M_P_ficka,mittr_10,Motortrafikled,Motorvag,Namn_132,Namn_193,Namns_133,OBJECTID,Passa_85,Passe_73,Plank_92,Provisorisk_vag,R_Gagata,R_Gangfartsomrade,R_Mater_301,R_P_ficka,R_Separ_500,R_VVIS,SHAPE_Length,slitl_25,Slitl_152,TattbebyggtOmrade,Tillg_169,TO_MEASURE,Trafi_86,Typ_369,Typ_a_55_29,TypAv_82,Under_14,Under_397,Vagha_6,Vagha_7,Vagkl_564,Vagnummer_ROLE,Vagtr_474,vagty_41
    -> Tester_7
Note: Filtrera bort överfart
Tester_7
    BOOL_OP = OR
    TEST_CLAUSE = TEST @Value(Konst_190) NOT_= överfart
    TEST_MODE = TEST
    PASSED -> LineCombiner
    FAILED -> Tester_3
LineCombiner
    ACCUM_ATTRS_NAME = Use Attributes From One Feature
    BREAK_CONNECTION_ATTRIBUTES = ROUTE_ID
    CLOSE = yes
    CONNECT_Z_MODE_LOOKUP = FIRST_WINS
    CONSIDER_NODE_ELEVATION_LOOKUP = NO
    DEAGGREGATE_GEOMETRY = Deaggregate
    JUNCTIONS_IGNORE_ATTRIBUTES = No
    LINES_AS_SEGMENTS = No
    NODED = END_NODED
    PRESERVE = no
    BREAK = no
    CONNECT_Z_MODE = First Wins
    CONSIDER_NODE_ELEVATION = no
    TOPOLOGY = End Noded
    LINE -> AttributeFilter
    LINE -> AttributeFilter_2

Bookmark: Ram träningsområde Kista
Default (reader DGNV8_1)
    -> Junction_10

Bookmark: Ram Testområde Kista
VERIF (reader FFS_6) [off]
    attributes: _creation_instance uint64
    -> Junction_10

Bookmark: Ram Testområde Kungsholmen
NewFeatureType (reader FFS_10) [off]
    attributes: _creation_instance uint64
    -> Junction_10

Bookmark: Åtgärda brolinje som behövs
Tester_3
    BOOL_OP = OR
    TEST_CLAUSE = TEST Typ_512 ATTRIBUTE_HAS_A_VALUE ""
    TEST_MODE = TEST
    PASSED -> Intersector_3
Intersector_3
    ATTRS_ACCUM_MODE = Use Attributes From One Feature
    CLEANING_TOLERANCE_LOOKUP = AUTO
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    INTERSECTED -> LineOnLineOverlayer [LINE]
    NODE -> Bufferer_2
Bufferer_2
    ANGLE = 22.5
    CAP_STYLE_LOOKUP = CAP_ARC
    CORNER_STYLE_LOOKUP = JOIN_ARC
    MODE = AREA
    OFFSET = 0.5
    OFFSET_UNITS = NONE
    PRECISION = APPROX
    CAP_STYLE = Arc
    CORNER_STYLE = Arc
    BUFFERED -> SpatialFilter_2 [Filter]
LineOnLineOverlayer
    ATTRS_ACCUM_MODE = Use Attributes From One Feature
    CLEANING_TOLERANCE_LOOKUP = AUTO
    DEAGGREGATE_INPUT = Yes
    GENERATE_LIST_DROP = NO
    OV_ATTR = _overlaps
    SEPARATE_COLLINEAR_SEGMENTS = No
    CLEANING_TOLERANCE = Automatic
    LINE -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> LineCombiner

Bookmark: 2_BK_CLEAN_TRÄNINGSOMRÅDE_KISTA
NewFeatureType (reader FFS_1)
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, Added_line varchar(4)
    -> Junction_9

Bookmark: 2_BK_CLEAN_TESTSOMRÅDE_KISTA
NewFeatureType (reader FFS_5) [off]
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> Junction_9

Bookmark: 2_BK_CLEAN_TESTOMRÅDE_KUNGSHOLMEN
NewFeatureType (reader FFS_11) [off]
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4)
    -> Junction_9

Bookmark: Lokalisera korsningar
Note: Hitta korsningsnoder
Intersector
    ATTRS_ACCUM_MODE = Use Attributes From One Feature
    CLEANING_TOLERANCE_LOOKUP = AUTO
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    INTERSECTED -> NeighborFinder [CANDIDATE]
    INTERSECTED -> Clipper_2 [CANDIDATE]
    INTERSECTED -> SpatialFilter_4 [Filter]
    NODE -> NeighborFinder [BASE]
NeighborFinder
    CANDIDATES_FIRST = No
    CLOSE_LIST_ATTRS_TO_INCLUDE_MODE = Selected Attributes
    CLOSE_LIST_NAME = neighbours
    INSERT_VERTEX = No
    MAX = 1
    MEASURES_FROM_CANDIDATE = Yes
    MEASURE_TYPE = Continuous
    MODE = Bases and Candidates
    TREAT_POLYGON_AS = Lines
    MATCHED -> ListElementCounter
Note: Räknar edges
ListElementCounter
    CNT_ATTR = _element_count
    LIST_NAME = neighbours{}
    -> Tester
Note: Korsning endast då varje nod > 3 egdes
Tester
    BOOL_OP = OR
    TEST_CLAUSE = TEST @Value(_element_count) > 2
    TEST_MODE = TEST
    PASSED -> Bufferer
    PASSED -> Junction_3
Note: Rektangulär buffer för området runt varje nod
Bufferer
    ANGLE = 22.5
    CAP_STYLE_LOOKUP = CAP_PROJECTING
    CORNER_STYLE_LOOKUP = JOIN_BEVEL
    MODE = AREA
    OFFSET = 20
    OFFSET_UNITS = NONE
    PRECISION = APPROX
    CAP_STYLE = Square
    CORNER_STYLE = Bevel
    BUFFERED -> Clipper_2 [CLIPPER]
    BUFFERED -> SpatialFilter_3 [Filter]
Note: PointOnAreaOverlayer : Point
Junction_3

Bookmark: Befintliga korsningsgeometrier i Kista träningsområde
Cirkulationsplats-gyB (reader DGNV8_2)
    -> GeometryFilter

Bookmark: Tillägg av redan definerade korsningar (enbart för träningsområde Kista)
Note: Ta bort punkter osv
GeometryFilter
    FILTER_MODE = SIMPLE
    FILTER_MULTI = FILTER_TYPES]"Point Line Area"]FME_CONTROLLER_QUERY_FILE]]FME_CONTROLLER_CHOICE]Simple
    Curve -> Clipper_4 [CANDIDATE]
    Area -> Clipper_4 [CANDIDATE]
Note: Klipp mot ramen
Clipper_4
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> GeometryFilter_2
Note: Ta bort punkter osv
GeometryFilter_2
    FILTER_MODE = SIMPLE
    FILTER_MULTI = FILTER_TYPES]"Point Line Area"]FME_CONTROLLER_QUERY_FILE]]FME_CONTROLLER_CHOICE]Simple
    Curve -> LineExtender
    Area -> SpatialFilter_3 [Candidate]
Note: Förläng ett linjesegment för att laga LOD1
LineExtender
    LEN = 0.01
    STRETCHED -> Junction_7
Note: LineOnAreaOverlayer_2 : Line
Junction_7
    -> Junction_8

Bookmark: Filter för att enbart ta med de nya korsningarna från Kista
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> SpatialFilter_4 [Candidate]
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Bufferer_3
Bufferer_3
    ANGLE = 22.5
    CAP_STYLE_LOOKUP = CAP_ARC
    CORNER_STYLE_LOOKUP = JOIN_ARC
    MODE = AREA
    OFFSET = 15
    OFFSET_UNITS = NONE
    PRECISION = APPROX
    CAP_STYLE = Arc
    CORNER_STYLE = Arc
    BUFFERED -> Clipper_2 [CLIPPER]

Bookmark: Skapa voronoi ytor för korsningar
Note: Addera nya vertices
Densifier
    INTERVAL = 2
    MODE_LOOKUP = xy_uniform
    MODE = Uniform Interval
    DENSIFIED -> Chopper
    DENSIFIED -> Intersector_2
Note: Dela upp linjen i punkter
Chopper
    DEAGGREGATE_INPUT = Deaggregate
    MAX_VERTICES = 1
    MODE_LOOKUP = VERTEX
    REMNANT_ATTR = _remnant
    MODE = By Vertex
    CHOPPED -> VoronoiDiagrammer_3 [POINTS]
Note: Skapa voronoiytor
VoronoiDiagrammer_3
    ACCUM_ATTRS_NAME = Use Attributes From One Feature
    VORONOI_RADIAL_LIMIT = 15
    VORONOI_POLYGONS -> SpatialFilter [Candidate]

Bookmark: Lokalisera slutpunkter för linjer
Note: Hitta slut och korsningsnoder
Intersector_2
    ATTRS_ACCUM_MODE = Use Attributes From One Feature
    CLEANING_TOLERANCE_LOOKUP = AUTO
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    INTERSECTED -> TopologyBuilder
    NODE -> TopologyBuilder
Note: Skapa edges attribut
TopologyBuilder
    ALLOW_CYCLES = No
    CLEANING_TOLERANCE_LOOKUP = AUTO
    DEAGGREGATE_INPUT = Yes
    GENERATION_MODE = INTERSECT
    LIST_NAME_EDGES = _edges
    MAX = 0
    OVERLAPPING_MODE = No
    START_EDGES = No
    BOUNDING_EDGES = All
    CLEANING_TOLERANCE = Automatic
    NODE -> ListElementCounter_2
Note: Räkna antalet edges per nod
ListElementCounter_2
    CNT_ATTR = _element_count
    LIST_NAME = _edges{}
    -> Tester_4
Note: Edges = 1 --> slutnod
Tester_4
    BOOL_OP = OR
    TEST_CLAUSE = TEST @Value(_element_count) = 1
    TEST_MODE = TEST
    PASSED -> SpatialFilter [Filter]

Bookmark: 5_MERGE_YTOR_TESTOMRÅDE_KUNGSHOLMEN
NewFeatureType (reader FFS_12) [off]
    attributes: BM_ANVD varchar(2), LOD1 varchar(9), LOD2 varchar(7), LOD3 varchar(5), ROUTE_ID varchar(38), Typ_512 varchar(23), GCM_t_502 varchar(37), Vagtr_474 varchar(10), 1_Temaklass varchar(7), 2_Klass varchar(7), 3_Subklass varchar(1), _count int64, Skymd varchar(2), DP_OID int64, CTYPE_NAME buffer, MARK_TEXT varchar(40), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4),
      _clipped char(3), _part_number uint64, _geometry_name buffer, 4_Track varchar(5), DP_OTYPE buffer, DP_OTYPE_NAME buffer, DP_SUBTYPE_NAME buffer, DP_CTYPE buffer, SYMBOL buffer, PRODUCT_NAME buffer, DP_MOD buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer,
      DP_DELETED buffer, TIDSPERIOD-UNDERLAG_GEOIDMODELL varchar(40), _grupp buffer, KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100),
      TRADSORT_NAMN varchar(100), TRADTYP_NAMN varchar(100), KRONRADIE real64, STAMDIAM real64, TRADHOJD real64, TRADSORT int32, TRADTYP int32, VET_NAMN int32, SVE_NAMN varchar(50), dp_otype int64, dp_oid int64, dp_ctype int64, dp_subtype int64, dp_occ int64, dp_lock int64, dp_deleted int64, dp_state int64, dp_dsp_flg int64, sub_c_type buffer, font buffer, font_id buffer, rotation real64, height real64, width real64, fid int64, _overlaps uint32, _length real64, _predicate buffer
    -> AttributeExposer

Bookmark: 5_MERGE_YTOR_TESTOMRÅDE_KISTA
NewFeatureType (reader FFS_7) [off]
    attributes: BM_ANVD varchar(2), LOD1 varchar(9), LOD2 varchar(7), LOD3 varchar(5), ROUTE_ID varchar(38), Typ_512 varchar(23), GCM_t_502 varchar(37), Vagtr_474 varchar(10), 1_Temaklass varchar(7), 2_Klass varchar(7), 3_Subklass varchar(1), _count int64, Skymd varchar(2), DP_OID int64, CTYPE_NAME buffer, MARK_TEXT varchar(40), 4_Slask varchar(4), _node_number uint32, _element_count uint64, _distance real64, _closest_candidate_x real64, _closest_candidate_y real64, _closest_base_x real64, _closest_base_y real64, _edge_id uint32, _right_face uint32, _left_face uint32, _faces uint32, _creation_instance uint64, Added_line varchar(4),
      _clipped char(3), _part_number uint64, _geometry_name buffer, 4_Track varchar(5), DP_OTYPE buffer, DP_OTYPE_NAME buffer, DP_SUBTYPE_NAME buffer, DP_CTYPE buffer, SYMBOL buffer, PRODUCT_NAME buffer, DP_MOD buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer, DP_OCCURRENCE buffer,
      DP_DELETED buffer, TIDSPERIOD-UNDERLAG_GEOIDMODELL varchar(40), _grupp buffer, KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32, VET_NAMN_NAMN varchar(100),
      TRADSORT_NAMN varchar(100), TRADTYP_NAMN varchar(100), KRONRADIE real64, STAMDIAM real64, TRADHOJD real64, TRADSORT int32, TRADTYP int32, VET_NAMN int32, SVE_NAMN varchar(50), dp_otype int64, dp_oid int64, dp_ctype int64, dp_subtype int64, dp_occ int64, dp_lock int64, dp_deleted int64, dp_state int64, dp_dsp_flg int64, sub_c_type buffer, font buffer, font_id buffer, rotation real64, height real64, width real64, fid int64, _overlaps uint32, _length real64, _predicate buffer
    -> AttributeExposer

Bookmark: 5_MERGE_YTOR_TRÄNINGSOMRÅDE_KISTA
NewFeatureType (reader FFS_2)
    attributes: BM_ANVD varchar(2), LOD1 varchar(9), LOD2 varchar(7), LOD3 varchar(5), ROUTE_ID varchar(38), Typ_512 varchar(23), GCM_t_502 varchar(37), Vagtr_474 varchar(10), 1_Temaklass varchar(11), 2_Klass varchar(25), 3_Subklass varchar(27), DP_OID int64, CTYPE_NAME buffer, MARK_TEXT varchar(40), 4_Slask varchar(4)
    -> AttributeExposer

Bookmark: Ta fram korsningsytor
Note: Dela ytor med linjer
LineOnAreaOverlayer
    CLEANING_TOLERANCE_LOOKUP = AUTO
    DEAGGREGATE_INPUT = Yes
    OVERLAY_TYPE = AREA_ON_LINE
    OV_ATTR = _overlaps
    CLEANING_TOLERANCE = Automatic
    AREA -> Clipper_3 [CLIPPER]
Note: Klipp mot BK-linjer
Clipper_3
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Dissolver_3
Note: Dissolvea för att hitta den total arean
Dissolver_3
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> Tester_2
Note: Snabbt area filter
Tester_2
    BOOL_OP = OR
    TEST_CLAUSE = TEST @Area() < 60
    TEST_MODE = TEST
    FAILED -> Counter_2
Note: Varje korsning får ett ID (count_intersection)
Counter_2
    CNT_ATTR = _count_intersction
    DOMAIN = counter
    SCOPE = Global
    START = 1
    -> GeometryCoercer_2

Bookmark: Snygga till varje korsnings hull
Note: Säkerställ line
GeometryCoercer_2
    GQUERY:
      for $geom in //geometry
      where $geom/count(parent::geometry) = 0
      return number($geom/@fme_id)
    KIND = fme_line
    COERCED -> Densifier_2
Note: Addera vertices
Densifier_2
    INTERVAL = 1
    MODE_LOOKUP = xy_uniform
    MODE = Uniform Interval
    DENSIFIED -> Chopper_2
Note: Konvertera till punkter
Chopper_2
    DEAGGREGATE_INPUT = Deaggregate
    MAX_VERTICES = 1
    MODE_LOOKUP = VERTEX
    REMNANT_ATTR = _remnant
    MODE = By Vertex
    CHOPPED -> HullAccumulator_2
Note: Ta fram en rakare hull
HullAccumulator_2
    3DMODETYPE = MAKE2D
    ACCUM_INPUT_ATTRS = Use Attributes From One Feature
    GROUP_BY = _count_intersction
    HULLTYPE = CONVEX
    3DMODE_PARAM = 2D
    HULLTYPE_PARAM = Convex ()
    HULL -> Clipper_6 [CANDIDATE]

Bookmark: Filtrera bort ensamma och icke-passande features
Note: Tester_6 [Tester] / Test Clauses: LogicLeft ValueOperatorRight Value@Value(1_Temaklass)=ByggnadOR@Value(1_Temaklass)=MissingOR@Value(LOD3)=Ej HuvudledOR@Value(1_Temaklass)=Stor ytaOR@Value(4_Track)=TrackAdvanced: / Preserve Feature Order: Per Output Port
Tester_6
    BOOL_OP = OR
    TEST_CLAUSE:
      TEST @Value(1_Temaklass) = Byggnad
      TEST @Value(1_Temaklass) = Missing
      TEST @Value(LOD3) = Ej Huvudled
      TEST @Value(1_Temaklass) = Stor yta
      TEST @Value(4_Track) = Track
    TEST_MODE = TEST
    FAILED -> NeighborFinder_2 [CANDIDATE]
NeighborFinder_2
    INSERT_VERTEX = No
    K = 1
    MAX = 0
    MEASURES_FROM_CANDIDATE = Yes
    MEASURE_TYPE = Continuous
    MODE = Candidates Only
    TREAT_POLYGON_AS = Lines
    MATCHED -> Clipper_7 [CLIPPER]

Bookmark: Intersections
Deaggregator
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> Dissolver
    DEAGGREGATED -> AttributeCreator_4
AttributeCreator_4
    ATTR_TABLE = SET_TO Intersection (varchar(12)) = Intersection
    -> Dissolver_4
    -> SpatialFilter_5 [Candidate]
Dissolver_4
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> UniqueIdentifierGenerator
UniqueIdentifierGenerator
    UUID_ATTR = _Intersection_UUID
    UUID_FORMAT = UUID_ONLY
    -> SpatialFilter_5 [Filter]
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Junction_4
Dissolver
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> FeatureColorSetter_2
FeatureColorSetter_2
    ALGORITHM = MANUAL
    COLOR = 0.666667,0,0
    FILL_COLOR = 0.666667,0,0
    MODE = Fixed
    COLORED -> AttributeCreator
AttributeCreator
    ATTR_TABLE = SET_TO Intersection (varchar(12)) = Intersection
    -> Junction_6

Bookmark: Sections och resterande BK
Deaggregator_2
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> Tester_5
Tester_5
    BOOL_OP = AND
    TEST_CLAUSE:
      TEST @Value(LOD1) = Vägtrafik
      TEST @Value(LOD3) != Ej Huvudled
      TEST 4_Track ATTRIBUTE_IS_MISSING ""
    TEST_MODE = TEST
    PASSED -> Dissolver_2
    PASSED -> AttributeCreator_3
    FAILED -> AttributeCreator_5
AttributeCreator_3
    ATTR_TABLE = SET_TO Section (varchar(7)) = Section
    -> Dissolver_5
    -> SpatialFilter_6 [Candidate]
Dissolver_5
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> UniqueIdentifierGenerator_2
UniqueIdentifierGenerator_2
    UUID_ATTR = _Section_UUID
    UUID_FORMAT = UUID_ONLY
    -> SpatialFilter_6 [Filter]
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Junction_4
Dissolver_2
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> LineOnAreaOverlayer_3 [AREA]
LineOnAreaOverlayer_3
    CLEANING_TOLERANCE_LOOKUP = AUTO
    DEAGGREGATE_INPUT = Yes
    OVERLAY_TYPE = AREA_ON_LINE
    OV_ATTR = _overlaps
    CLEANING_TOLERANCE = Automatic
    AREA -> FeatureColorSetter
FeatureColorSetter
    ALGORITHM = MANUAL
    COLOR = 1,0,0
    FILL_COLOR = 1,0,0
    MODE = Fixed
    COLORED -> AttributeCreator_2
AttributeCreator_5
    ATTR_TABLE = SET_TO Not_Road (varchar(8)) = Not_road
    -> Junction_4
    -> AttributeCreator_2
AttributeCreator_2
    ATTR_TABLE = SET_TO Section (varchar(12)) = Section
    -> Junction_6

Bookmark: 6_SEC_&_INTERSEC_TRÄNINGSOMRÅDE_KISTA LOD1
NewFeatureType (writer FFS_3) [off]
    attributes: Intersection varchar(12), BM_ANVD varchar(2), LOD1 varchar(9), LOD2 varchar(7), LOD3 varchar(5), ROUTE_ID varchar(38), Typ_512 varchar(23), GCM_t_502 varchar(37), Vagtr_474 varchar(10), 1_Temaklass varchar(11), 2_Klass varchar(25), 3_Subklass varchar(27), DP_OID int64, CTYPE_NAME buffer, MARK_TEXT varchar(40), 4_Slask varchar(4), _count int64, Skymd varchar(2), _node_number uint32, _element_count uint64, _distance real64, _closest_candidate_x real64, _closest_candidate_y real64, _closest_base_x real64, _closest_base_y real64, _edge_id uint32, _right_face uint32, _left_face uint32, _faces uint32, _creation_instance uint64,
      Added_line varchar(4), _clipped char(3), _part_number uint64, _geometry_name buffer, 4_Track varchar(5), DP_OTYPE buffer, DP_OTYPE_NAME buffer, DP_SUBTYPE_NAME buffer, DP_CTYPE buffer, SYMBOL buffer, PRODUCT_NAME buffer, DP_MOD buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer,
      DP_OCCURRENCE buffer, DP_DELETED buffer, TIDSPERIOD-UNDERLAG_GEOIDMODELL varchar(40), _grupp buffer, KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32,
      VET_NAMN_NAMN varchar(100), TRADSORT_NAMN varchar(100), TRADTYP_NAMN varchar(100), KRONRADIE real64, STAMDIAM real64, TRADHOJD real64, TRADSORT int32, TRADTYP int32, VET_NAMN int32, SVE_NAMN varchar(50), dp_otype int64, dp_oid int64, dp_ctype int64, dp_subtype int64, dp_occ int64, dp_lock int64, dp_deleted int64, dp_state int64, dp_dsp_flg int64, sub_c_type buffer, font buffer, font_id buffer, rotation real64, height real64, width real64, fid int64, _overlaps uint32, _length real64, _predicate buffer, Section varchar(12),
      Not_Road varchar(8)

Bookmark: 6_SEC_&_INTERSEC_TRÄNINGSOMRÅDE_KISTA LOD2
NewFeatureType (writer FFS_4) [off]
    attributes: Not_Road varchar(8), BM_ANVD varchar(2), LOD1 varchar(9), LOD2 varchar(7), LOD3 varchar(5), ROUTE_ID varchar(38), Typ_512 varchar(23), GCM_t_502 varchar(37), Vagtr_474 varchar(10), 1_Temaklass varchar(11), 2_Klass varchar(25), 3_Subklass varchar(27), DP_OID int64, CTYPE_NAME buffer, MARK_TEXT varchar(40), 4_Slask varchar(4), _count int64, Skymd varchar(2), _node_number uint32, _element_count uint64, _distance real64, _closest_candidate_x real64, _closest_candidate_y real64, _closest_base_x real64, _closest_base_y real64, _edge_id uint32, _right_face uint32, _left_face uint32, _faces uint32, _creation_instance uint64,
      Added_line varchar(4), _clipped char(3), _part_number uint64, _geometry_name buffer, 4_Track varchar(5), DP_OTYPE buffer, DP_OTYPE_NAME buffer, DP_SUBTYPE_NAME buffer, DP_CTYPE buffer, SYMBOL buffer, PRODUCT_NAME buffer, DP_MOD buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer,
      DP_OCCURRENCE buffer, DP_DELETED buffer, TIDSPERIOD-UNDERLAG_GEOIDMODELL varchar(40), _grupp buffer, KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32,
      VET_NAMN_NAMN varchar(100), TRADSORT_NAMN varchar(100), TRADTYP_NAMN varchar(100), KRONRADIE real64, STAMDIAM real64, TRADHOJD real64, TRADSORT int32, TRADTYP int32, VET_NAMN int32, SVE_NAMN varchar(50), dp_otype int64, dp_oid int64, dp_ctype int64, dp_subtype int64, dp_occ int64, dp_lock int64, dp_deleted int64, dp_state int64, dp_dsp_flg int64, sub_c_type buffer, font buffer, font_id buffer, rotation real64, height real64, width real64, fid int64, _overlaps uint32, _length real64, _predicate buffer, Intersection varchar(12),
      _Intersection_UUID char(36), Section varchar(7), _Section_UUID char(36)

Bookmark: 6_SEC_&_INTERSEC_TESTOMRÅDE_KISTA LOD2
NewFeatureType (writer FFS_9) [off]
    attributes: Not_Road varchar(8), BM_ANVD varchar(2), LOD1 varchar(9), LOD2 varchar(7), LOD3 varchar(5), ROUTE_ID varchar(38), Typ_512 varchar(23), GCM_t_502 varchar(37), Vagtr_474 varchar(10), 1_Temaklass varchar(11), 2_Klass varchar(25), 3_Subklass varchar(27), DP_OID int64, CTYPE_NAME buffer, MARK_TEXT varchar(40), 4_Slask varchar(4), _count int64, Skymd varchar(2), _node_number uint32, _element_count uint64, _distance real64, _closest_candidate_x real64, _closest_candidate_y real64, _closest_base_x real64, _closest_base_y real64, _edge_id uint32, _right_face uint32, _left_face uint32, _faces uint32, _creation_instance uint64,
      Added_line varchar(4), _clipped char(3), _part_number uint64, _geometry_name buffer, 4_Track varchar(5), DP_OTYPE buffer, DP_OTYPE_NAME buffer, DP_SUBTYPE_NAME buffer, DP_CTYPE buffer, SYMBOL buffer, PRODUCT_NAME buffer, DP_MOD buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer,
      DP_OCCURRENCE buffer, DP_DELETED buffer, TIDSPERIOD-UNDERLAG_GEOIDMODELL varchar(40), _grupp buffer, KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32,
      VET_NAMN_NAMN varchar(100), TRADSORT_NAMN varchar(100), TRADTYP_NAMN varchar(100), KRONRADIE real64, STAMDIAM real64, TRADHOJD real64, TRADSORT int32, TRADTYP int32, VET_NAMN int32, SVE_NAMN varchar(50), dp_otype int64, dp_oid int64, dp_ctype int64, dp_subtype int64, dp_occ int64, dp_lock int64, dp_deleted int64, dp_state int64, dp_dsp_flg int64, sub_c_type buffer, font buffer, font_id buffer, rotation real64, height real64, width real64, fid int64, _overlaps uint32, _length real64, _predicate buffer, Intersection varchar(12),
      _Intersection_UUID char(36), Section varchar(7), _Section_UUID char(36)

Bookmark: 6_SEC_&_INTERSEC_TESTOMRÅDE_KUNGSHOLMEN LOD2
NewFeatureType (writer FFS_13) [off]
    attributes: Not_Road varchar(8), BM_ANVD varchar(2), LOD1 varchar(9), LOD2 varchar(7), LOD3 varchar(5), ROUTE_ID varchar(38), Typ_512 varchar(23), GCM_t_502 varchar(37), Vagtr_474 varchar(10), 1_Temaklass varchar(11), 2_Klass varchar(25), 3_Subklass varchar(27), DP_OID int64, CTYPE_NAME buffer, MARK_TEXT varchar(40), 4_Slask varchar(4), _count int64, Skymd varchar(2), _node_number uint32, _element_count uint64, _distance real64, _closest_candidate_x real64, _closest_candidate_y real64, _closest_base_x real64, _closest_base_y real64, _edge_id uint32, _right_face uint32, _left_face uint32, _faces uint32, _creation_instance uint64,
      Added_line varchar(4), _clipped char(3), _part_number uint64, _geometry_name buffer, 4_Track varchar(5), DP_OTYPE buffer, DP_OTYPE_NAME buffer, DP_SUBTYPE_NAME buffer, DP_CTYPE buffer, SYMBOL buffer, PRODUCT_NAME buffer, DP_MOD buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer, _whereBaggis buffer,
      DP_OCCURRENCE buffer, DP_DELETED buffer, TIDSPERIOD-UNDERLAG_GEOIDMODELL varchar(40), _grupp buffer, KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2), VARIANT int32, VANSTER int32,
      VET_NAMN_NAMN varchar(100), TRADSORT_NAMN varchar(100), TRADTYP_NAMN varchar(100), KRONRADIE real64, STAMDIAM real64, TRADHOJD real64, TRADSORT int32, TRADTYP int32, VET_NAMN int32, SVE_NAMN varchar(50), dp_otype int64, dp_oid int64, dp_ctype int64, dp_subtype int64, dp_occ int64, dp_lock int64, dp_deleted int64, dp_state int64, dp_dsp_flg int64, sub_c_type buffer, font buffer, font_id buffer, rotation real64, height real64, width real64, fid int64, _overlaps uint32, _length real64, _predicate buffer, Intersection varchar(12),
      _Intersection_UUID char(36), Section varchar(7), _Section_UUID char(36)
