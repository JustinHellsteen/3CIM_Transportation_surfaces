FME workspace 7_CITYGML.fmw

Parameters:
- SourceDataset_FFS = C:\Users\ai31986\HCP\Examensarbete\FME Projekt workspaces\6_INTERSECTIONS\OUTPUT\6_INTERSECTIONS_LOD1.ffs   # Source FME Feature Store (FFS) File(s)
- SourceDataset_FFS_6 = C:\Users\ai31986\HCP\Examensarbete\FME Projekt workspaces\6_INTERSECTIONS\OUTPUT\6_INTERSECTIONS_LOD2.ffs   # Source FME Feature Store (FFS) File(s)
- SourceDataset_DGNV8 = C:\Users\ai31986\HCP\Examensarbete\Data\Ramar\Urklipp runt Kistaäng.dgn   # Source Bentley MicroStation Design File(s)
- SourceDataset_OGCGEOPACKAGE = C:\Users\ai31986\HCP\Examensarbete\Data\Parkdata\TK_Parkkarta_dpMapExport_GPKG_2024-06-12.gpkg   # GeoPackage File
- FEATURE_TYPES =
- SourceDataset_FILEGDB = C:\Users\ai31986\HCP\Examensarbete\Data\NVDB\Trafikverket_NVDB_väg-homogeniserade_2024-04-19_JUSTERAD-LAGE.gdb   # File Geodatabase
- SourceDataset_FFS_5 = C:\Users\ai31986\HCP\Examensarbete\FME Projekt workspaces\2_BK_CLEAN\OUTPUT\2_BK_CLEAN.ffs   # Source FME Feature Store (FFS) File(s)
- DestDataset_CITYGML_3 = $(FME_MF_DIR)OUTPUT\7_FINAL_06_11v2.gml   # Destination CityGML Document

Readers:
- FFS_1: FFS from $(SourceDataset_FFS) in SWEREF-99-18-00
- FFS_2: FFS from $(SourceDataset_FFS_6) in SWEREF-99-18-00
- DGNV8_1: DGNV8 from $(SourceDataset_DGNV8) in SWEREF-99-18-00
- OGCGEOPACKAGE_1: OGCGEOPACKAGE from $(SourceDataset_OGCGEOPACKAGE) in SWEREF-99-18-00
- FILEGDB_1: FILEGDB from $(SourceDataset_FILEGDB) in SWEREF-99-TM
- FFS_3: FFS from $(SourceDataset_FFS_5) in SWEREF-99-18-00

Writers:
- CITYGML_1: CITYGML to $(DestDataset_CITYGML_3) in SWEREF-99-18-00

Note: Clipper_2 : Clipper
Junction_2
    -> Junction_3
Note: Default
Junction_3
Note: Clipper_4 : Clipper
Junction_6
    -> Junction_8
Note: Default
Junction_8
    -> Clipper_4 [CLIPPER]
Tester_35
    BOOL_OP = OR
    TEST_CLAUSE = TEST @Value(Section) = Section
    TEST_MODE = TEST
    PASSED -> SpatialFilter_5 [Candidate]
    FAILED -> Tester_36
Tester_36
    BOOL_OP = OR
    TEST_CLAUSE = TEST @Value(Intersection) = Intersection
    TEST_MODE = TEST
    PASSED -> SpatialFilter_6 [Candidate]
    FAILED -> Dissolver
    FAILED -> SpatialFilter_4 [Candidate]
Dissolver
    ACCUM_INPUT_ATTRS = Use Attributes From One Feature
    CLEANING_TOLERANCE_LOOKUP = AUTO
    CONNECT_Z_MODE_LOOKUP = FIRST_WINS
    DEAGGREGATE_INPUT = Yes
    GROUP_BY = 4_Track
    CLEANING_TOLERANCE = Automatic
    CONNECT_Z_MODE = First Wins
    AREA -> UniqueIdentifierGenerator_10
UniqueIdentifierGenerator_10
    UUID_ATTR = UUID_Section
    UUID_FORMAT = UUID_ONLY
    -> StringConcatenator_2
StringConcatenator_2
    ACTION = Create New Attribute
    PARM_LINE = fme_basicstring:11%20:Section_id_@Value(UUID_Section)
    VAL_ATTR = _result
    -> AttributeManager_4
AttributeManager_4
    ATTR_TABLE:
      SET_TO UUID_Section (char(36)) = @Value(_result)
      REMOVE _result (buffer)
    -> SpatialFilter_4 [Filter]
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator
AttributeCreator
    ATTR_TABLE = SET_TO Section (varchar(7)) = Section
    -> Junction_11
AttributeFilter_8
    ATTR_NAME = LOD2
    ATTR_VALUES = <Empty>,<Missing>,<Null>,<Unfiltered>,Cykelväg,GC-väg,Gångväg,Körbana
    <MISSING> -> Junction_23
    <UNFILTERED> -> Junction_23
    Cykelväg -> Junction_22
    GC-väg -> Junction_22
    Gångväg -> Junction_22
    Körbana -> Junction_22
Junction_23
    -> AttributeCreator_14
AttributeCreator_14
    ATTR_TABLE = SET_TO gml_id (varchar(7)) = AUX_id_
    -> UniqueIdentifierGenerator_2
UniqueIdentifierGenerator_2
    UUID_ATTR = uuid
    UUID_FORMAT = UUID_ONLY
    -> StringConcatenator_4
StringConcatenator_4
    ACTION = Create New Attribute
    PARM_LINE = fme_basicstring:14%12:@Value(gml_id)@Value(uuid)
    VAL_ATTR = gml_id
    -> AttributeRemover_16
AttributeRemover_16
    REMOVE_ATTRS = _clipped,_count,_geometry_name,_part_number,_predicate,uuid
    -> Junction_24
Junction_22
    -> AttributeCreator_30
Junction_24
    -> AttributeCreator_32
AttributeCreator_41
    ATTR_TABLE = SET_TO gml_name (varchar(200))
    -> Tester_27
Tester_27
    BOOL_OP = COMPOSITE
    COMPOSITE_TEST = 1 AND 2
    TEST_CLAUSE:
      TEST Intersection ATTRIBUTE_HAS_A_VALUE ""
      TEST @Value(citygml_function{0}) = 10100
    TEST_MODE = TEST
    PASSED -> SpatialFilter_13 [Candidate]
    FAILED -> Tester_24
Tester_24
    BOOL_OP = COMPOSITE
    COMPOSITE_TEST = 1 AND 2
    TEST_CLAUSE:
      TEST Section ATTRIBUTE_HAS_A_VALUE ""
      TEST @Value(citygml_function{0}) = 10100
    TEST_MODE = TEST
    PASSED -> SpatialFilter_12 [Candidate]
    FAILED -> Junction_30
Junction_11
    -> Junction_20
Note: CenterPointReplacer : Input
Junction_20
    -> Junction_21
Note: Junction_11 : Output
Junction_21
    -> CenterPointReplacer
CenterPointReplacer
    POINTTYPE = INSIDE
    POINT -> AttributeRemover
AttributeRemover
    REMOVE_ATTRS = _clipped,_count,_geometry_name,_length,_overlaps,_part_number,_predicate,1_Temaklass,2_Klass,3_Subklass,4_Slask,4_Track,BM_ANVD,citygml_surface_material,CTYPE_NAME,DP_OID,GCM_t_502,Intersection,LOD1,LOD2,LOD3,MARK_TEXT,Not_Road,ROUTE_ID,Section,sub_c_type,Typ_512,Vagtr_474
    -> SpatialFilter_2 [Filter]
AttributeFilter_10
    ATTR_NAME = Typ_512
    ATTR_VALUES = <Empty>,<Missing>,<Null>,<Unfiltered>,FME_NULL_VALUE,Huvudgata,Infartsväg/Utfartsväg,Kvartersväg,Lokalgata liten,Lokalgata stor,Parkeringsområdesväg
    Huvudgata -> Junction_27
    Lokalgata liten -> Junction_27
    Lokalgata stor -> Junction_27
Junction_27
    -> Junction_31
    -> Junction_32
Junction_30
    -> AttributeRemover_27
AttributeRemover_27
    REMOVE_ATTRS = ROUTE_ID
    -> Tester_40
Tester_40
    BOOL_OP = AND
    TEST_CLAUSE:
      TEST Utfyllnad ATTRIBUTE_IS_MISSING ""
      TEST @Value(LOD2) != Separering
    TEST_MODE = TEST
    PASSED -> SpatialRelator_6 [Requestor]
    FAILED -> SpatialRelator_6 [Requestor]
SpatialRelator_6
    AGGREGATE_HANDLING = Yes
    CALC_CARD = No
    CURVE_BOUNDARY_RULE_PARAM = Default Rule
    LIST_ATTRS_TO_INCLUDE = ROUTE_ID
    LIST_NAME = _list
    PREDICATES = INTERSECTS
    SUCCESS_ATTR = _related_suppliers
    -> ListConcatenator_5
ListConcatenator_5
    DROP_EMPTY_PARTS = Yes
    LIST_ATTR = _list{}.ROUTE_ID
    SEP = ,
    VAL_ATTR = _concatenated
    -> AttributeCreator_42
AttributeCreator_42
    ATTR_TABLE = SET_TO externalReference{0}.externalObject.name (varchar(200)) = @Value(_concatenated)
    -> AttributeCreator_43
AttributeCreator_43
    ATTR_TABLE = SET_TO externalReference{0}.informationSystem (varchar(26)) = Trafikverket_NVDB_ROUTE_ID
    -> 2DForcer_3
2DForcer_3
    2D -> Orientor_3
Orientor_3
    KIND = LEFT_HAND_RULE
    ORIENTED -> AttributeCreator_44
AttributeCreator_44
    ATTR_TABLE:
      SET_TO citygml_target_uri (varchar(200))
      SET_TO citygml_feature_role (varchar(200))
      SET_TO citygml_generalizes_to{0}.xlink_href (varchar(200))
      SET_TO citygml_relative_to_water (varchar(200))
      SET_TO citygml_appearance{0}.xlink_href (varchar(200))
      SET_TO citygml_usage{0} (varchar(200))
      SET_TO citygml_usage{0}.codeSpace (varchar(200))
      SET_TO citygml_traffic_area{0}.xlink_href (varchar(200))
      SET_TO citygml_auxiliary_traffic_area{0}.xlink_href (varchar(200))
      SET_TO citygml_creationDate (varchar(200))
      SET_TO citygml_terminationDate (date)
      SET_TO citygml_function{0}.codeSpace (varchar(96)) = https://github.com/3CIM/3CIM2.0/blob/main/kodlistor/Transportation/TrafficArea_function.xml
      SET_TO citygml_class_codeSpace (varchar(103)) = https://github.com/3CIM/Public-files/blob/main/kodlistor/Transportation/TransportationComplex_class.xml
      SET_TO citygml_feature_role_attr_name (varchar(200))
      SET_TO citygml_feature_role_attr_val (varchar(200))
      SET_TO citygml_relative_to_terrain (varchar(33)) = substantiallyAboveAndBelowTerrain
      SET_TO trecim_absolut_lagesosakerhet_hojd{0} (varchar(200))
      SET_TO trecim_absolut_lagesosakerhet_plan{0} (varchar(200))
      SET_TO trecim_co_class{0}.trecim_co_class_trecim_co_class_id (varchar(200))
      SET_TO trecim_co_class{0}.trecim_co_class_trecim_co_class_kod{0} (varchar(200))
      SET_TO trecim_co_class{0}.trecim_co_class_trecim_co_class_version (varchar(200))
      SET_TO trecim_metod_ihojd_tidsperiod_fran{0} (varchar(200))
      SET_TO trecim_metod_ihojd_tidsperiod_till{0} (varchar(200))
      SET_TO trecim_metod_ihojd_typ{0} (varchar(200))
      SET_TO trecim_metod_ihojd_typ{0}.codeSpace (varchar(200))
      SET_TO trecim_metod_iplan_tidsperiod_fran{0} (varchar(200))
      SET_TO trecim_metod_iplan_tidsperiod_till{0} (varchar(200))
      SET_TO trecim_metod_iplan_typ{0} (varchar(200))
      SET_TO trecim_metod_iplan_typ{0}.codeSpace (varchar(200))
      SET_TO trecim_objekt_uuid{0} (varchar(200))
      SET_TO trecim_osakert_lage{0} (varchar(200))
      SET_TO trecim_osakert_lage{0}.codeSpace (varchar(200))
      SET_TO trecim_status{0} (varchar(200))
      SET_TO trecim_status{0}.codeSpace (varchar(200))
      SET_TO trecim_tidpunkt_for_kontroll_av_geometri{0} (varchar(200))
      SET_TO trecim_tidpunkt_for_lagesbestamning{0} (varchar(200))
      SET_TO trecim_valid_from{0} (varchar(200))
      SET_TO trecim_valid_to{0} (varchar(200))
      SET_TO trecim_version{0} (varchar(200))
      SET_TO trecim_intersection_of_road{0}.xlink_href (varchar(200))
      SET_TO trecim_section_of_road{0}.xlink_href (varchar(200))
    -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator_4
AttributeCreator_4
    ATTR_TABLE = SET_TO citygml_surface_material_codeSpace (varchar(103)) = https://github.com/3CIM/Public-files/blob/main/kodlistor/Transportation/TrafficArea_surfaceMaterial.xml
    -> AttributeRemover_2
AttributeRemover_2
    REMOVE_ATTRS = 1_Temaklass,2_Klass,3_Subklass,4_Slask,BM_ANVD,CTYPE_NAME,DP_OID,GCM_t_502,Intersection,LOD1,LOD3,MARK_TEXT,Not_Road,Section,Typ_512,Utfyllnad,Vagtr_474,_concatenated,_length,_overlaps,_predicate,_related_suppliers,fme_fill_color,sub_c_type
    -> Tester
Tester
    BOOL_OP = OR
    TEST_CLAUSE = TEST UUID_Intersection ATTRIBUTE_HAS_A_VALUE ""
    TEST_MODE = TEST
    PASSED -> AttributeCreator_2
    FAILED -> AttributeCreator_3
AttributeCreator_2
    ATTR_TABLE = SET_TO gml_parent_id (varchar(200)) = @Value(UUID_Intersection)
    -> AttributeFilter
    -> Junction_5
AttributeCreator_3
    ATTR_TABLE = SET_TO gml_parent_id (varchar(200)) = @Value(UUID_Section)
    -> AttributeFilter
    -> Junction_5
Junction_5
    -> Dissolver_4
Dissolver_4
    ACCUM_INPUT_ATTRS = Use Attributes From One Feature
    CLEANING_TOLERANCE_LOOKUP = AUTO
    CONNECT_Z_MODE_LOOKUP = FIRST_WINS
    DEAGGREGATE_INPUT = Yes
    GROUP_BY = UUID_Intersection UUID_Section
    CLEANING_TOLERANCE = Automatic
    CONNECT_Z_MODE = First Wins
    AREA -> AttributeCreator_5
AttributeCreator_5
    ATTR_TABLE = SET_TO citygml_level_of_detail{0} (uint8) = 1
    -> Tester_2
    -> Tester_5
Tester_5
    BOOL_OP = OR
    TEST_CLAUSE = TEST 4_Track ATTRIBUTE_HAS_A_VALUE ""
    TEST_MODE = TEST
    PASSED -> UniqueIdentifierGenerator_6
    PASSED -> Sampler
    FAILED -> Tester_6
Note: AttributeRemover_8 : Output
Junction_10
    -> AttributeRemover_10
Tester_6
    BOOL_OP = OR
    TEST_CLAUSE = TEST @Value(citygml_function{0}) = 10500
    TEST_MODE = TEST
    PASSED -> AttributeManager_12
    FAILED -> UniqueIdentifierGenerator_11
Note: AttributeRemover_19 : Output
Junction_19
    -> AttributeRemover_10
Tester_2
    BOOL_OP = OR
    TEST_CLAUSE = TEST UUID_Intersection ATTRIBUTE_HAS_A_VALUE ""
    TEST_MODE = TEST
    PASSED -> AttributeManager
    FAILED -> Tester_3
AttributeFilter
    ATTR_NAME = LOD2
    ATTR_VALUES = <Empty>,<Missing>,<Null>,<Unfiltered>,Cykelväg,GC-väg,Gångväg,Körbana,Separering
    <MISSING> -> AttributeRemover_21
    Cykelväg -> Junction_4
    GC-väg -> Junction_4
    Gångväg -> Junction_4
    Körbana -> Junction_4
    Separering -> AttributeRemover_21
Junction_4
    -> AttributeCreator_7
TransportationComplex (writer CITYGML_1)
    attributes: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
Note: AttributeRemover_17 : Output
Junction_14
    -> AttributeRemover_10
AttributeRemover_10
    REMOVE_ATTRS = citygml_appearance{0}.xlink_href,citygml_auxiliary_traffic_area{0}.xlink_href,citygml_class,citygml_class_codeSpace,citygml_creationDate,citygml_feature_role,citygml_feature_role_attr_name,citygml_feature_role_attr_val,citygml_function{0},citygml_function{0}.codeSpace,citygml_generalizes_to{0}.xlink_href,citygml_level_of_detail{0},citygml_relative_to_terrain,citygml_relative_to_water,citygml_surface_material,citygml_surface_material_codeSpace,citygml_target_uri,citygml_terminationDate,citygml_traffic_area{0}.xlink_href,citygml_usage{0},citygml_usage{0}.codeSpace,externalReference{0}.externalObject.name,externalReference{0}.informationSystem,gml_description,gml_name,gml_parent_id,trecim_absolut_lagesosakerhet_hojd{0},trecim_absolut_lagesosakerhet_plan{0},trecim_co_class{0}.trecim_co_class_trecim_co_class_id,trecim_co_class{0}.trecim_co_class_trecim_co_class_kod{0},trecim_co_class{0}.trecim_co_class_trecim_co_class_version,trecim_intersection_of_road{0}.xlink_href,trecim_intersection_of_track{0}.xlink_href,trecim_metod_ihojd_tidsperiod_fran{0},trecim_metod_ihojd_tidsperiod_till{0},trecim_metod_ihojd_typ{0},trecim_metod_ihojd_typ{0}.codeSpace,trecim_metod_iplan_tidsperiod_fran{0},trecim_metod_iplan_tidsperiod_till{0},trecim_metod_iplan_typ{0},trecim_metod_iplan_typ{0}.codeSpace,trecim_objekt_uuid{0},trecim_osakert_lage{0},trecim_osakert_lage{0}.codeSpace,trecim_section_of_road{0}.xlink_href,trecim_section_of_track{0}.xlink_href,trecim_status{0},trecim_status{0}.codeSpace,trecim_tidpunkt_for_kontroll_av_geometri{0},trecim_tidpunkt_for_lagesbestamning{0},trecim_valid_from{0},trecim_valid_to{0},trecim_version{0}
    -> AttributeRenamer
AttributeRenamer
    ATTR_TABLE = RENAME_SET_DEFAULT gml_id > help_id
    KEEP_RENAMED_ONLY = no
    MISSING_INPUT_ATTRS = REMOVE
    -> CenterPointReplacer_2
CenterPointReplacer_2
    POINTTYPE = INSIDE
    POINT -> SpatialFilter_3 [Filter]
    POINT -> SpatialFilter_7 [Filter]

Bookmark: RAM Kista Träningsområde
Default (reader DGNV8_1)
    -> Clipper [CLIPPER]
    -> Junction_2
    -> Clipper_3 [CLIPPER]
    -> Junction_6

Bookmark: Parkdata
barkflis_ej_plantering_polygon (reader OGCGEOPACKAGE_1)
    attributes: dp_ctype int, dp_deleted int, dp_dsp_flg int, dp_lock int, dp_occ int, dp_oid int, dp_otype int, dp_state int, dp_subtype int, sub_c_type text, make text, obj_id text, prod_name text, surface_course text, surface_treatment text, fid int,PrimaryKey, font text, font_id text, height double, rotation double, width double
    -> Clipper [CANDIDATE]
    -> Clipper_3 [CANDIDATE]

Bookmark: Förarbete Parkdata
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> AttributeRemover_11
AttributeRemover_11
    REMOVE_ATTRS = _clipped,dp_ctype,dp_deleted,dp_dsp_flg,dp_lock,dp_occ,dp_oid,dp_otype,dp_state,dp_subtype,fid,fme_feature_type,font,font_id,height,make,obj_id,prod_name,rotation,surface_course,surface_treatment,width
    -> AttributeFilter_4
AttributeFilter_4
    ATTR_NAME = sub_c_type
    ATTR_VALUES = <Empty>,<Missing>,<Null>,<Unfiltered>,Annuellrabatt - gyB,Asfalt parkväg - gyB,Baksand - gyB,Bark/flis (ej plantering) - gyB,Betongplattor - gyB,Bruksbuskage - gyB,Bruksgräsyta - gyB,Bruksmur - gyB,Brukspark - gyB,Bäck, vattendrag - gyB,Dagvattenbrunn - sB,Död ved/biodepå - sB,Fontän - gyB,Grus parkväg - gyB,Grus, stenmjöl - gyB,Gummibelagd yta - gyB,Gungställningsfack/hänggunga - sB,Gångfålla med grind/bom - sB,Klippt häck - gyB,Kullersten - gyB,Ledstång - glB,Lek- och klätterställning - sB,Lekhus - sB,Luftbrunn - sB,Marksten av betong - gyB,Nätstängsel - glB,Ospecificerat objekt - gyB,Perenna växter - gyB,Pergola - glB,Prydnadsbuskage - gyB,Rutschbana - sB,Sandlådesarg - glB,Skräpkorg - sB,Slåtter utan uppsamling - gyB,Slåtteräng - gyB,Smågatsten - gyB,Soffa/bänk, fast - sB,Soffa/bänkbord, löst - sB,Strid sand - gyB,Säckställ - sB,Torg - gyB,Trappa - gyB,Träbelagd yta - gyB,Trädbevuxen naturmark, skog - gyB,Vippgunga/gungbräda - sB,Växtdamm/dagvattendamm - gyB,Yta med annan funktion än park - gyB,Öppen naturmark - gyB,Övrig lekutrustning - sB,Övrig natursten - gyB
    Asfalt parkväg - gyB -> Junction_7
    Betongplattor - gyB -> Junction_7
    Grus parkväg - gyB -> Junction_7
    Grus, stenmjöl - gyB -> Junction_7
    Gummibelagd yta - gyB -> Junction_7
    Kullersten - gyB -> Junction_7
    Marksten av betong - gyB -> Junction_7
    Smågatsten - gyB -> Junction_7
    Övrig natursten - gyB -> Junction_7
Junction_7
    -> Tester_10
Tester_10
    BOOL_OP = OR
    TEST_CLAUSE = TEST @Area() > 3
    TEST_MODE = TEST
    PASSED -> SpatialFilter [Candidate]

Bookmark: Förarbete Parkdata
Clipper_3
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> AttributeRemover_15
AttributeRemover_15
    REMOVE_ATTRS = _clipped,dp_ctype,dp_deleted,dp_dsp_flg,dp_lock,dp_occ,dp_oid,dp_otype,dp_state,dp_subtype,fid,fme_feature_type,font,font_id,height,make,obj_id,prod_name,rotation,surface_course,surface_treatment,width
    -> AttributeFilter_2
AttributeFilter_2
    ATTR_NAME = sub_c_type
    ATTR_VALUES = <Empty>,<Missing>,<Null>,<Unfiltered>,Annuellrabatt - gyB,Asfalt parkväg - gyB,Baksand - gyB,Bark/flis (ej plantering) - gyB,Betongplattor - gyB,Bruksbuskage - gyB,Bruksgräsyta - gyB,Bruksmur - gyB,Brukspark - gyB,Bäck, vattendrag - gyB,Dagvattenbrunn - sB,Död ved/biodepå - sB,Fontän - gyB,Grus parkväg - gyB,Grus, stenmjöl - gyB,Gummibelagd yta - gyB,Gungställningsfack/hänggunga - sB,Gångfålla med grind/bom - sB,Klippt häck - gyB,Kullersten - gyB,Ledstång - glB,Lek- och klätterställning - sB,Lekhus - sB,Luftbrunn - sB,Marksten av betong - gyB,Nätstängsel - glB,Ospecificerat objekt - gyB,Perenna växter - gyB,Pergola - glB,Prydnadsbuskage - gyB,Rutschbana - sB,Sandlådesarg - glB,Skräpkorg - sB,Slåtter utan uppsamling - gyB,Slåtteräng - gyB,Smågatsten - gyB,Soffa/bänk, fast - sB,Soffa/bänkbord, löst - sB,Strid sand - gyB,Säckställ - sB,Torg - gyB,Trappa - gyB,Träbelagd yta - gyB,Trädbevuxen naturmark, skog - gyB,Vippgunga/gungbräda - sB,Växtdamm/dagvattendamm - gyB,Yta med annan funktion än park - gyB,Öppen naturmark - gyB,Övrig lekutrustning - sB,Övrig natursten - gyB
    Asfalt parkväg - gyB -> Junction_16
    Betongplattor - gyB -> Junction_16
    Grus parkväg - gyB -> Junction_16
    Grus, stenmjöl - gyB -> Junction_16
    Gummibelagd yta - gyB -> Junction_16
    Kullersten - gyB -> Junction_16
    Marksten av betong - gyB -> Junction_16
    Smågatsten - gyB -> Junction_16
    Övrig natursten - gyB -> Junction_16
Junction_16
    -> Tester_9
Tester_9
    BOOL_OP = OR
    TEST_CLAUSE = TEST @Area() > 3
    TEST_MODE = TEST
    PASSED -> SpatialFilter_9 [Candidate]

Bookmark: 6_INTERSECTIONS_LOD2
NewFeatureType (reader FFS_2)
    attributes: Not_Road varchar(8), BM_ANVD varchar(2), LOD1 varchar(9), LOD2 varchar(7), LOD3 varchar(5), ROUTE_ID varchar(38), Typ_512 varchar(23), GCM_t_502 varchar(37), Vagtr_474 varchar(10), 1_Temaklass varchar(11), 2_Klass varchar(25), 3_Subklass varchar(27), DP_OID int64, CTYPE_NAME buffer, MARK_TEXT varchar(40), 4_Slask varchar(4), 4_Track varchar(200), _count int64, _clipped char(9), _part_number uint64, _geometry_name buffer, Intersection varchar(12), Section varchar(7)
    -> AttributeExposer_3
    -> AttributeExposer_4

Bookmark: Sub_c_type fanns redan --> ta bort
AttributeExposer_3
    ATTR_TABLE = sub_c_type,
    -> AttributeRemover_12
AttributeRemover_12
    REMOVE_ATTRS = sub_c_type
    -> Tester_37
Tester_37
    BOOL_OP = AND
    TEST_CLAUSE:
      TEST @Value(1_Temaklass) != Stor yta
      TEST @Value(1_Temaklass) != Missing
      TEST @Value(1_Temaklass) != Byggnad
      TEST @Value(1_Temaklass) != Anläggning
    TEST_MODE = TEST
    PASSED -> Junction_13

Bookmark: Surface material
Junction_13
    -> SpatialFilter [Filter]
    -> LineOnAreaOverlayer [AREA]
    -> SpatialFilter_8 [Candidate]
SpatialFilter
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> Dissolver_3
Dissolver_3
    ACCUM_INPUT_ATTRS = Use Attributes From One Feature
    CLEANING_TOLERANCE_LOOKUP = AUTO
    CONNECT_Z_MODE_LOOKUP = FIRST_WINS
    DEAGGREGATE_INPUT = Yes
    GROUP_BY = sub_c_type
    CLEANING_TOLERANCE = Automatic
    CONNECT_Z_MODE = First Wins
    AREA -> Tester_11
Tester_11
    BOOL_OP = OR
    TEST_CLAUSE = TEST @Area() > 100
    TEST_MODE = TEST
    PASSED -> CenterlineReplacer
CenterlineReplacer
    MODE = APPROX_CENTER_LINE
    CENTERLINE -> LineOnAreaOverlayer [LINE]
LineOnAreaOverlayer
    CLEANING_TOLERANCE_LOOKUP = AUTO
    DEAGGREGATE_INPUT = Yes
    OVERLAY_TYPE = LINE_ON_AREA
    OV_ATTR = _overlaps
    CLEANING_TOLERANCE = Automatic
    LINE -> LengthCalculator
LengthCalculator
    DIM = 2
    LEN_ATTR = _length
    MULT = 1
    -> Tester_12
Tester_12
    BOOL_OP = OR
    TEST_CLAUSE = TEST @Value(_length) > 13.5
    TEST_MODE = TEST
    PASSED -> SpatialFilter_8 [Filter]
SpatialFilter_8
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeFilter_5
    FAILED -> Tester_13
AttributeFilter_5
    ATTR_NAME = sub_c_type
    ATTR_VALUES = <Empty>,<Missing>,<Null>,<Unfiltered>,Asfalt parkväg - gyB,Betongplattor - gyB,Grus parkväg - gyB
    Asfalt parkväg - gyB -> Junction
    Betongplattor - gyB -> AttributeCreator_13
    Grus parkväg - gyB -> AttributeCreator_12
AttributeCreator_13
    ATTR_TABLE = SET_TO citygml_surface_material (varchar(6)) = 621701
    -> Junction
AttributeCreator_12
    ATTR_TABLE = SET_TO citygml_surface_material (varchar(6)) = 622100
    -> Junction
Tester_13
    BOOL_OP = AND
    TEST_CLAUSE:
      TEST @Value(LOD2) = Körbana
      TEST @Value(LOD3) != Ej Huvudled
    TEST_MODE = TEST
    PASSED -> AttributeCreator_29
    FAILED -> AttributeCreator_31
AttributeCreator_29
    ATTR_TABLE = SET_TO citygml_surface_material (varchar(6)) = 621100
    -> Junction
AttributeCreator_31
    ATTR_TABLE = SET_TO citygml_surface_material (varchar(6))
    -> Junction
Junction
    -> Tester_35

Bookmark: Sub_c_type fanns redan --> ta bort
AttributeExposer_4
    ATTR_TABLE = sub_c_type,
    -> AttributeRemover_14
AttributeRemover_14
    REMOVE_ATTRS = sub_c_type
    -> Tester_8
Tester_8
    BOOL_OP = AND
    TEST_CLAUSE:
      TEST @Value(1_Temaklass) != Stor yta
      TEST @Value(1_Temaklass) != Missing
      TEST @Value(1_Temaklass) != Byggnad
      TEST @Value(1_Temaklass) != Anläggning
    TEST_MODE = TEST
    PASSED -> Junction_18

Bookmark: Surface material
Junction_18
    -> SpatialFilter_9 [Filter]
    -> LineOnAreaOverlayer_2 [AREA]
    -> SpatialFilter_10 [Candidate]
SpatialFilter_9
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> Dissolver_2
Dissolver_2
    ACCUM_INPUT_ATTRS = Use Attributes From One Feature
    CLEANING_TOLERANCE_LOOKUP = AUTO
    CONNECT_Z_MODE_LOOKUP = FIRST_WINS
    DEAGGREGATE_INPUT = Yes
    GROUP_BY = sub_c_type
    CLEANING_TOLERANCE = Automatic
    CONNECT_Z_MODE = First Wins
    AREA -> Tester_14
Tester_14
    BOOL_OP = OR
    TEST_CLAUSE = TEST @Area() > 100
    TEST_MODE = TEST
    PASSED -> CenterlineReplacer_2
CenterlineReplacer_2
    MODE = APPROX_CENTER_LINE
    CENTERLINE -> LineOnAreaOverlayer_2 [LINE]
LineOnAreaOverlayer_2
    CLEANING_TOLERANCE_LOOKUP = AUTO
    DEAGGREGATE_INPUT = Yes
    OVERLAY_TYPE = LINE_ON_AREA
    OV_ATTR = _overlaps
    CLEANING_TOLERANCE = Automatic
    LINE -> LengthCalculator_2
LengthCalculator_2
    DIM = 2
    LEN_ATTR = _length
    MULT = 1
    -> Tester_18
Tester_18
    BOOL_OP = OR
    TEST_CLAUSE = TEST @Value(_length) > 13.5
    TEST_MODE = TEST
    PASSED -> SpatialFilter_10 [Filter]
SpatialFilter_10
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeFilter_7
    FAILED -> Tester_19
AttributeFilter_7
    ATTR_NAME = sub_c_type
    ATTR_VALUES = <Empty>,<Missing>,<Null>,<Unfiltered>,Asfalt parkväg - gyB,Betongplattor - gyB,Grus parkväg - gyB
    Asfalt parkväg - gyB -> Junction_17
    Betongplattor - gyB -> AttributeCreator_10
    Grus parkväg - gyB -> AttributeCreator_11
AttributeCreator_10
    ATTR_TABLE = SET_TO citygml_surface_material (varchar(6)) = 621701
    -> Junction_17
AttributeCreator_11
    ATTR_TABLE = SET_TO citygml_surface_material (varchar(6)) = 622100
    -> Junction_17
Tester_19
    BOOL_OP = AND
    TEST_CLAUSE:
      TEST @Value(LOD2) = Körbana
      TEST @Value(LOD3) != Ej Huvudled
    TEST_MODE = TEST
    PASSED -> AttributeCreator_8
    FAILED -> AttributeCreator_9
AttributeCreator_8
    ATTR_TABLE = SET_TO citygml_surface_material (varchar(6)) = 621100
    -> Junction_17
AttributeCreator_9
    ATTR_TABLE = SET_TO citygml_surface_material (varchar(6))
    -> Junction_17
Junction_17
    -> AttributeFilter_8

Bookmark: Ge samtliga gml_id
AttributeCreator_30
    ATTR_TABLE = SET_TO gml_id (varchar(7)) = TA_id_
    -> UniqueIdentifierGenerator_3
UniqueIdentifierGenerator_3
    UUID_ATTR = uuid
    UUID_FORMAT = UUID_ONLY
    -> StringConcatenator_5
StringConcatenator_5
    ACTION = Create New Attribute
    PARM_LINE = fme_basicstring:14%12:@Value(gml_id)@Value(uuid)
    VAL_ATTR = gml_id
    -> AttributeRemover_22
AttributeRemover_22
    REMOVE_ATTRS = _clipped,_count,_geometry_name,_part_number,_predicate,uuid
    -> Junction_24

Bookmark: CLASS, FUNCTION AND DESCRIPTION
AttributeCreator_32
    ATTR_TABLE = SET_TO citygml_class (varchar(9)) = 10000
    -> AttributeFilter_9
AttributeFilter_9
    ATTR_NAME = LOD2
    ATTR_VALUES = <Empty>,<Missing>,<Null>,<Unfiltered>,Cykelväg,GC-väg,Gångväg,Körbana,Separering
    <MISSING> -> AttributeCreator_35
    Cykelväg -> AttributeCreator_33
    GC-väg -> AttributeCreator_34
    Gångväg -> AttributeCreator_35
    Körbana -> Tester_20
    Separering -> AttributeCreator_36
AttributeCreator_33
    ATTR_TABLE:
      SET_TO citygml_function{0} (uint16) = 10300
      SET_TO gml_description (varchar(19)) = Vägtrafik, Cykelväg
    -> Junction_25
AttributeCreator_34
    ATTR_TABLE:
      SET_TO citygml_function{0} (uint16) = 10400
      SET_TO gml_description (varchar(17)) = Vägtrafik, GC-väg
    -> Junction_25
AttributeCreator_35
    ATTR_TABLE:
      SET_TO citygml_function{0} (uint16) = 10200
      SET_TO gml_description (varchar(18)) = Vägtrafik, Gångväg
    -> Junction_25
Tester_20
    BOOL_OP = OR
    TEST_CLAUSE = TEST @Value(LOD3) = Ej Huvudled
    TEST_MODE = TEST
    PASSED -> AttributeCreator_37
    FAILED -> AttributeExposer_5
AttributeCreator_37
    ATTR_TABLE:
      SET_TO citygml_function{0} (uint16) = 10500
      SET_TO gml_description (varchar(15)) = Vägtrafik, Torg
    -> Junction_25
AttributeExposer_5
    ATTR_TABLE = fme_fill_color,
    -> Tester_21
Tester_21
    BOOL_OP = OR
    TEST_CLAUSE = TEST @Value(fme_fill_color) = 1,0,1
    TEST_MODE = TEST
    PASSED -> AttributeCreator_39
    FAILED -> AttributeCreator_38
AttributeCreator_39
    ATTR_TABLE:
      SET_TO citygml_function{0} (uint16) = 10200
      SET_TO gml_description (varchar(18)) = Vägtrafik, Gångväg
    -> AttributeCreator_40
AttributeCreator_40
    ATTR_TABLE = SET_TO Utfyllnad (varchar(2)) = Ja
    -> Junction_25
AttributeCreator_38
    ATTR_TABLE:
      SET_TO citygml_function{0} (uint16) = 10100
      SET_TO gml_description (varchar(18)) = Vägtrafik, Körbana
    -> Junction_25
AttributeCreator_36
    ATTR_TABLE:
      SET_TO citygml_function{0} (uint16) = 10200
      SET_TO gml_description (varchar(21)) = Vägtrafik, Separering
    -> Junction_25
Junction_25
    -> AttributeCreator_41

Bookmark: LOD1
NewFeatureType (reader FFS_1)
    attributes: Section varchar(12), BM_ANVD varchar(2), LOD1 varchar(9), LOD2 varchar(7), LOD3 varchar(5), ROUTE_ID varchar(38), Typ_512 varchar(23), GCM_t_502 varchar(37), Vagtr_474 varchar(10), 1_Temaklass varchar(11), 2_Klass varchar(25), 3_Subklass varchar(27), DP_OID int64, CTYPE_NAME buffer, MARK_TEXT varchar(40), 4_Slask varchar(4), 4_Track varchar(200), _count int64, _clipped char(9), _part_number uint64, _geometry_name buffer, Intersection varchar(12), Not_Road varchar(8)
    -> Tester_32
    -> Tester_33

Bookmark: Intersection
Tester_33
    BOOL_OP = AND
    TEST_CLAUSE:
      TEST @Value(Intersection) = @Value(Intersection)
      TEST @Value(1_Temaklass) != Stor yta
      TEST @Value(1_Temaklass) != Missing
      TEST @Value(1_Temaklass) != Byggnad
      TEST @Value(1_Temaklass) != Anläggning
      TEST 4_Track ATTRIBUTE_IS_MISSING ""
      TEST @Value(LOD3) != Ej Huvudled
      TEST @Value(Section) != Section
    TEST_MODE = TEST
    PASSED -> AttributeRemover_6
AttributeRemover_6
    REMOVE_ATTRS = _clipped,_count,_geometry_name,_part_number,1_Temaklass,2_Klass,3_Subklass,4_Slask,4_Track,BM_ANVD,CTYPE_NAME,DP_OID,GCM_t_502,Intersection,LOD1,LOD2,LOD3,MARK_TEXT,Not_Road,ROUTE_ID,Section,Typ_512,Vagtr_474
    -> UniqueIdentifierGenerator_8
UniqueIdentifierGenerator_8
    UUID_ATTR = UUID_Intersection
    UUID_FORMAT = UUID_ONLY
    -> StringConcatenator_3
StringConcatenator_3
    ACTION = Create New Attribute
    PARM_LINE = fme_basicstring:16%25:Intersection_id_@Value(UUID_Intersection)
    VAL_ATTR = _result
    -> AttributeManager_5
AttributeManager_5
    ATTR_TABLE:
      SET_TO UUID_Intersection (char(36)) = @Value(_result)
      REMOVE _result (buffer)
    -> Bufferer_3
Bufferer_3
    ANGLE = 22.5
    CAP_STYLE_LOOKUP = CAP_ARC
    CORNER_STYLE_LOOKUP = JOIN_ARC
    MODE = AREA
    OFFSET = -0.01
    OFFSET_UNITS = NONE
    PRECISION = APPROX
    CAP_STYLE = Arc
    CORNER_STYLE = Arc
    BUFFERED -> SpatialFilter_6 [Filter]
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Junction_11

Bookmark: Section
Tester_32
    BOOL_OP = AND
    TEST_CLAUSE:
      TEST @Value(Section) = Section
      TEST @Value(1_Temaklass) != Stor yta
      TEST @Value(1_Temaklass) != Missing
      TEST @Value(1_Temaklass) != Byggnad
      TEST @Value(1_Temaklass) != Anläggning
      TEST 4_Track ATTRIBUTE_IS_MISSING ""
      TEST @Value(LOD3) != Ej Huvudled
    TEST_MODE = TEST
    PASSED -> AttributeRemover_5
AttributeRemover_5
    REMOVE_ATTRS = _clipped,_count,_geometry_name,_part_number,1_Temaklass,2_Klass,3_Subklass,4_Slask,4_Track,BM_ANVD,CTYPE_NAME,DP_OID,GCM_t_502,Intersection,LOD1,LOD2,LOD3,MARK_TEXT,Not_Road,ROUTE_ID,Section,Typ_512,Vagtr_474
    -> UniqueIdentifierGenerator_7
UniqueIdentifierGenerator_7
    UUID_ATTR = UUID_Section
    UUID_FORMAT = UUID_ONLY
    -> StringConcatenator
StringConcatenator
    ACTION = Create New Attribute
    PARM_LINE = fme_basicstring:11%20:Section_id_@Value(UUID_Section)
    VAL_ATTR = _result
    -> AttributeManager_3
AttributeManager_3
    ATTR_TABLE:
      SET_TO UUID_Section (char(36)) = @Value(_result)
      REMOVE _result (buffer)
    -> Bufferer
Bufferer
    ANGLE = 22.5
    CAP_STYLE_LOOKUP = CAP_ARC
    CORNER_STYLE_LOOKUP = JOIN_ARC
    MODE = AREA
    OFFSET = -0.01
    OFFSET_UNITS = NONE
    PRECISION = APPROX
    CAP_STYLE = Arc
    CORNER_STYLE = Arc
    BUFFERED -> SpatialFilter_5 [Filter]
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Junction_11

Bookmark: NVDB
TNE_FT_VAGDATA (reader FILEGDB_1)
    attributes: ROUTE_ID text(38), FROM_MEASURE double, TO_MEASURE double, Korfa_524 int, F_ATK_Matplats smallint, B_ATK_Matplats smallint, F_Avser_28 text(3), B_Avser_28 text(3), F_Hogst_24 double, B_Hogst_24 double, Hogst_36 double, Hogst_46 double, Hogst_55_30 double, Typ_a_55_29 text(16), Ident_191 text(3000), Konst_190 text(23), Langd_192 double, Namn_193 text(3000), Brunn___Slamsugning smallint, L_Mater_301 text(15), R_Mater_301 text(15), Barig_64 text(25), Barig_504 text(25), C_Rekbilvagcykeltrafik smallint, F_Cirkulationsplats smallint, B_Cirkulationsplats smallint, entre_380 text(36), drift_2 text(34), LageF_83 text(42), TypAv_82 text(59),
      Framk_161 text(47), Klass_181 text(1), FPV_k_309 text(39), Funktionellt_priovagnat smallint, F_ForbjudenFardriktning smallint, B_ForbjudenFardriktning smallint, F_ForbudTrafik smallint, B_ForbudTrafik smallint, F_Beskr_454 text(3000), B_Beskr_454 text(3000), Namn_130 text(3000), Typ_512 text(23), GCM_belyst smallint, GCM_passage smallint, Passa_85 text(93), Trafi_86 text(22), L_Separ_500 text(13), R_Separ_500 text(13), GCM_t_502 text(37), L_Gagata smallint, R_Gagata smallint, L_Gangfartsomrade smallint, R_Gangfartsomrade smallint, F_Hogst_225 text(10), B_Hogst_225 text(10), Hallplats smallint, Plank_92 text(3000), F_Korfa_517 text(9), B_Korfa_517 text(9), mittr_10 text(8),
      Motortrafikled smallint, Motorvag smallint, Provisorisk_vag smallint, L_P_ficka smallint, R_P_ficka smallint, M_P_ficka smallint, Slitl_152 text(6), TattbebyggtOmrade smallint, Tillg_169 text(1), Under_397 text(48), L_VVIS smallint, R_VVIS smallint, slitl_25 text(15), Bredd_156 double, Hinde_72 text(39), Passe_73 double, Vagha_7 text(3000), Vagha_6 text(8), Forva_9 text(22), Avvik_540 text(8), Kateg_380 text(17), Europ_16 smallint, Huvud_13_1 int, Lanst_15 int, Under_14 int, Vagtr_474 text(10), korfa_52 text(17), vagty_41 text(24), Typ_369 text(23), Namn_132 text(3000),
      Namns_133 text(8), Kommu_141 text(3000), Vagkl_564 text(1), Vagnummer_ROLE text(11), OBJECTID objectid, SHAPE_Length double
    -> Reprojector_3

Bookmark: Förarbete med vägdata
Reprojector_3
    DEST = SWEREF-99-18-00
    INTERPOLATION_TYPE = ,NearestNeighbor
    RASTER_CELL_SIZE_LOOKUP = ,PreserveCells
    RASTER_TOLERANCE = 0.0
    SOURCE = SWEREF-99-TM
    INTERPOLATION_TYPE_NAME = Nearest Neighbor
    RASTER_CELL_SIZE = Preserve Cells
    REPROJECTED -> Clipper_4 [CANDIDATE]
Clipper_4
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> AttributeRemover_23
Note: Rensa attribut
AttributeRemover_23
    REMOVE_ATTRS = _clipped,Avvik_540,B_ATK_Matplats,B_Avser_28,B_Beskr_454,B_Cirkulationsplats,B_ForbjudenFardriktning,B_ForbudTrafik,B_Hogst_24,B_Hogst_225,B_Korfa_517,Barig_64,Barig_504,Bredd_156,Brunn___Slamsugning,C_Rekbilvagcykeltrafik,drift_2,entre_380,Europ_16,F_ATK_Matplats,F_Avser_28,F_Beskr_454,F_Cirkulationsplats,F_ForbjudenFardriktning,F_ForbudTrafik,F_Hogst_24,F_Hogst_225,F_Korfa_517,Forva_9,FPV_k_309,Framk_161,FROM_MEASURE,Funktionellt_priovagnat,GCM_belyst,GCM_passage,Hallplats,Hinde_72,Hogst_36,Hogst_46,Hogst_55_30,Huvud_13_1,Ident_191,Kateg_380,Klass_181,Kommu_141,korfa_52,Korfa_524,L_Gagata,L_Gangfartsomrade,L_Mater_301,L_P_ficka,L_Separ_500,L_VVIS,LageF_83,Langd_192,Lanst_15,M_P_ficka,mittr_10,Motortrafikled,Motorvag,Namn_132,Namn_193,Namns_133,OBJECTID,Passa_85,Passe_73,Plank_92,Provisorisk_vag,R_Gagata,R_Gangfartsomrade,R_Mater_301,R_P_ficka,R_Separ_500,R_VVIS,SHAPE_Length,slitl_25,Slitl_152,TattbebyggtOmrade,Tillg_169,TO_MEASURE,Trafi_86,Typ_369,Typ_a_55_29,TypAv_82,Under_14,Under_397,Vagha_6,Vagha_7,Vagkl_564,Vagnummer_ROLE,Vagtr_474,vagty_41
    -> Tester_22
Note: Filtrera bort överfart
Tester_22
    BOOL_OP = OR
    TEST_CLAUSE = TEST @Value(Konst_190) NOT_= överfart
    TEST_MODE = TEST
    PASSED -> LineCombiner_2
    FAILED -> Tester_23
Tester_23
    BOOL_OP = OR
    TEST_CLAUSE = TEST Typ_512 ATTRIBUTE_HAS_A_VALUE ""
    TEST_MODE = TEST
    PASSED -> Intersector_2
Intersector_2
    ATTRS_ACCUM_MODE = Use Attributes From One Feature
    CLEANING_TOLERANCE_LOOKUP = AUTO
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    INTERSECTED -> LineOnLineOverlayer_2 [LINE]
    NODE -> Bufferer_4
Bufferer_4
    ANGLE = 22.5
    CAP_STYLE_LOOKUP = CAP_ARC
    CORNER_STYLE_LOOKUP = JOIN_ARC
    MODE = AREA
    OFFSET = 0.5
    OFFSET_UNITS = NONE
    PRECISION = APPROX
    CAP_STYLE = Arc
    CORNER_STYLE = Arc
    BUFFERED -> SpatialFilter_11 [Filter]
LineOnLineOverlayer_2
    ATTRS_ACCUM_MODE = Use Attributes From One Feature
    CLEANING_TOLERANCE_LOOKUP = AUTO
    DEAGGREGATE_INPUT = Yes
    GENERATE_LIST_DROP = NO
    OV_ATTR = _overlaps
    SEPARATE_COLLINEAR_SEGMENTS = No
    CLEANING_TOLERANCE = Automatic
    LINE -> SpatialFilter_11 [Candidate]
SpatialFilter_11
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> LineCombiner_2
LineCombiner_2
    ACCUM_ATTRS_NAME = Use Attributes From One Feature
    BREAK_CONNECTION_ATTRIBUTES = ROUTE_ID
    CLOSE = yes
    CONNECT_Z_MODE_LOOKUP = FIRST_WINS
    CONSIDER_NODE_ELEVATION_LOOKUP = NO
    DEAGGREGATE_GEOMETRY = Deaggregate
    JUNCTIONS_IGNORE_ATTRIBUTES = No
    LINES_AS_SEGMENTS = No
    NODED = END_NODED
    PRESERVE = no
    BREAK = no
    CONNECT_Z_MODE = First Wins
    CONSIDER_NODE_ELEVATION = no
    TOPOLOGY = End Noded
    LINE -> AttributeRemover_24
AttributeRemover_24
    REMOVE_ATTRS = _bygglov_diarienummer_public,_closest_base_x,_closest_base_y,_closest_candidate_x,_closest_candidate_y,_distance,_edge_id,_element_count,_faces,_grupp,_left_face,_matched_records,_node_number,_overlaps,_predicate,_related_suppliers,_right_face,_segments,_whereBaggis,1_Temaklass,2_Klass,3_Subklass,4_Slask,absolutLagesosakerhetHojd,absolutLagesosakerhetPlan,Added_line,ANL_NAMN,BREDD,CA_NAME,CTABLE,CTYPE_NAME,DIARIENR,DP_CTYPE,DP_DELETED,DP_MOD,DP_OCCURRENCE,DP_OID,DP_OTYPE,DP_OTYPE_NAME,DP_SIGN,DP_SUBTYPE,DP_SUBTYPE_NAME,FILL_COLOR,GCM_t_502,HUSNR,INM_LAGE,INM_LAGE_TEXT,INMATNINGSANV,KANTSTOD,KANTSTOD_TEXT,KOM_ID,Konst_190,KONSTRUERAD,KONSTRUERAD_TEXT,KRONRADIE,LANDMARKE,MARK,MARK_TEXT,MATANVISNINGAR,metodIHojdTyp,metodIPlanTidsperiodFran,metodIPlanTidsperiodTill,metodIPlanTyp,OSKARP,OSKARP_TEXT,PROD_CLASS_ID,PROD_ELEV,PROD_PLANE,PRODUCT_NAME,RELATIV_HOJD,Skymd,STADIUM,STAMDIAM,SVE_NAMN,SYMBOL,tidpunktForKontrollAvGeometri,tidpunktForLagesbestamning,TIDSPERIOD-UNDERLAG_GEOIDMODELL,TRADHOJD,TRADSORT,TRADSORT_NAMN,TRADTYP,TRADTYP_NAMN,UUID_BYGGNAD,VANSTER,VANSTER_TEXT,VARIANT,VARIANT_NAMN,VET_NAMN,VET_NAMN_NAMN
    -> AttributeFilter_10
    -> SpatialRelator_6 [Supplier]

Bookmark: 2_BK_CLEAN
NewFeatureType (reader FFS_3)
    attributes: Skymd varchar(2), 1_Temaklass varchar(7), 2_Klass varchar(7), 3_Subklass varchar(1), DP_OTYPE buffer, DP_OTYPE_NAME buffer, DP_SUBTYPE_NAME buffer, DP_CTYPE buffer, SYMBOL buffer, DP_OID int64, PRODUCT_NAME buffer, DP_MOD buffer, CTYPE_NAME buffer, PROD_ELEV buffer, PROD_PLANE buffer, tidpunktForLagesbestamning buffer, tidpunktForKontrollAvGeometri buffer, metodIPlanTidsperiodFran datetime, metodIPlanTidsperiodTill datetime, MATANVISNINGAR varchar(200), STADIUM varchar(40), absolutLagesosakerhetPlan varchar(40), metodIPlanTyp varchar(80), absolutLagesosakerhetHojd varchar(40), metodIHojdTyp varchar(80), DP_SIGN buffer, FILL_COLOR varchar(200), CTABLE buffer, DP_SUBTYPE buffer, PROD_CLASS_ID buffer,
      _whereBaggis buffer, DP_OCCURRENCE buffer, DP_DELETED buffer, TIDSPERIOD-UNDERLAG_GEOIDMODELL varchar(40), _grupp buffer, MARK_TEXT varchar(40), KANTSTOD_TEXT varchar(100), KANTSTOD int32, MARK int32, _matched_records uint32, INM_LAGE_TEXT varchar(100), _bygglov_diarienummer_public varchar(200), DIARIENR int32, INMATNINGSANV int32, CA_NAME varchar(80), KOM_ID varchar(200), HUSNR varchar(200), UUID_BYGGNAD varchar(200), _related_suppliers uint32, INM_LAGE int32, LANDMARKE int32, VARIANT_NAMN varchar(100), OSKARP_TEXT varchar(100), VANSTER_TEXT varchar(100), KONSTRUERAD_TEXT varchar(100), ANL_NAMN varchar(40), BREDD number(6,2), KONSTRUERAD int32, OSKARP int32, RELATIV_HOJD number(6,2),
      VARIANT int32, VANSTER int32, VET_NAMN_NAMN varchar(100), TRADSORT_NAMN varchar(100), TRADTYP_NAMN varchar(100), KRONRADIE real64, STAMDIAM real64, TRADHOJD real64, TRADSORT int32, TRADTYP int32, VET_NAMN int32, SVE_NAMN varchar(50), 4_Slask varchar(4), _node_number uint32, _element_count uint64, _distance real64, _closest_candidate_x real64, _closest_candidate_y real64, _closest_base_x real64, _closest_base_y real64, _edge_id uint32, _right_face uint32, _left_face uint32, _faces uint32, Added_line varchar(4)
    -> LineOnLineOverlayer_2 [LINE]

Bookmark: GML name section
Junction_32
    -> SpatialRelator_3 [Supplier]
    -> SpatialFilter_12 [Filter]
SpatialFilter_12
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialRelator_3 [Requestor]
    FAILED -> Junction_28
SpatialRelator_3
    AGGREGATE_HANDLING = Yes
    CALC_CARD = No
    CURVE_BOUNDARY_RULE_PARAM = Default Rule
    LIST_ATTRS_TO_INCLUDE = Namn_130 ROUTE_ID Typ_512
    LIST_NAME = _relationships
    PREDICATES = INTERSECTS
    SUCCESS_ATTR = _related_suppliers
    -> Tester_25
Tester_25
    BOOL_OP = OR
    TEST_CLAUSE = TEST _relationships{1}.Namn_130 ATTRIBUTE_IS_MISSING ""
    TEST_MODE = TEST
    PASSED -> ListIndexer_3
    FAILED -> ListHistogrammer_3
ListIndexer_3
    INDEX = 0
    LIST_ATTR = _relationships{}
    -> AttributeManager_6
AttributeManager_6
    ATTR_TABLE = RENAME_SET_VALUE Namn_130 > gml_name (varchar(3000))
    -> Junction_28
AttributeManager_14
    ATTR_TABLE = SET_TO gml_name (varchar(200)) = @Value(Gatunamn)
    -> Junction_28
Junction_28
    -> AttributeRemover_25
AttributeRemover_25
    LIST_ATTRS = _nameHist{} _nameHist{}.count _nameHist{}.value _relationships{} _relationships{}.Namn_130 _relationships{}.ROUTE_ID _relationships{}.Typ_512 _relationships{}.de9im _relationships{}.pass{} pass{}
    REMOVE_ATTRS = Gatunamn,_nameHist{0}.count,_nameHist{0}.value,_predicate,_related_suppliers,_relationships{0}.Namn_130,_relationships{0}.ROUTE_ID,_relationships{0}.Typ_512,_relationships{0}.de9im,_relationships{0}.pass{0},de9im,pass{0}
    -> Junction_30

Bookmark: Namn
ListHistogrammer_3
    LIST_NAME = _nameHist
    SRC_LIST = _relationships{}.Namn_130
    -> Tester_26
Tester_26
    BOOL_OP = OR
    TEST_CLAUSE = TEST _nameHist{1}.value ATTRIBUTE_HAS_A_VALUE ""
    TEST_MODE = TEST
    PASSED -> ListConcatenator_3
    FAILED -> AttributeManager_7
ListConcatenator_3
    DROP_EMPTY_PARTS = Yes
    LIST_ATTR = _nameHist{}.value
    SEP = ", "
    VAL_ATTR = Gatunamn
    -> AttributeManager_14
AttributeManager_7
    ATTR_TABLE = SET_TO gml_name (varchar(200)) = @Value(_nameHist{0}.value)
    -> Junction_28

Bookmark: GML name intersection
Junction_31
    -> SpatialFilter_13 [Filter]
    -> SpatialRelator_4 [Supplier]
SpatialFilter_13
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialRelator_4 [Requestor]
    FAILED -> Junction_29
SpatialRelator_4
    AGGREGATE_HANDLING = Yes
    CALC_CARD = No
    CURVE_BOUNDARY_RULE_PARAM = Default Rule
    LIST_ATTRS_TO_INCLUDE = Namn_130 ROUTE_ID Typ_512
    LIST_NAME = _relationships
    PREDICATES = INTERSECTS
    SUCCESS_ATTR = _related_suppliers
    -> Tester_28
Tester_28
    BOOL_OP = OR
    TEST_CLAUSE = TEST _relationships{1}.Namn_130 ATTRIBUTE_IS_MISSING ""
    TEST_MODE = TEST
    PASSED -> ListIndexer_5
    FAILED -> ListHistogrammer_4
ListIndexer_5
    INDEX = 0
    LIST_ATTR = _relationships{}
    -> AttributeManager_15
AttributeManager_15
    ATTR_TABLE = RENAME_SET_VALUE Namn_130 > gml_name (varchar(3000))
    -> Junction_29
AttributeManager_17
    ATTR_TABLE = SET_TO gml_name (varchar(200)) = @Value(Gatunamn)
    -> Junction_29
Junction_29
    -> AttributeRemover_26
AttributeRemover_26
    LIST_ATTRS = _nameHist{} _nameHist{}.count _nameHist{}.value _relationships{} _relationships{}.Namn_130 _relationships{}.ROUTE_ID _relationships{}.Typ_512 _relationships{}.de9im _relationships{}.pass{} pass{}
    REMOVE_ATTRS = Gatunamn,_nameHist{0}.count,_nameHist{0}.value,_predicate,_related_suppliers,_relationships{0}.Namn_130,_relationships{0}.ROUTE_ID,_relationships{0}.Typ_512,_relationships{0}.de9im,_relationships{0}.pass{0},de9im,pass{0}
    -> Junction_30

Bookmark: Namn
ListHistogrammer_4
    LIST_NAME = _nameHist
    SRC_LIST = _relationships{}.Namn_130
    -> Tester_29
Tester_29
    BOOL_OP = OR
    TEST_CLAUSE = TEST _nameHist{1}.value ATTRIBUTE_HAS_A_VALUE ""
    TEST_MODE = TEST
    PASSED -> ListConcatenator_4
    FAILED -> AttributeManager_16
ListConcatenator_4
    DROP_EMPTY_PARTS = Yes
    LIST_ATTR = _nameHist{}.value
    SEP = ", "
    VAL_ATTR = Gatunamn
    -> AttributeManager_17
AttributeManager_16
    ATTR_TABLE = SET_TO gml_name (varchar(200)) = @Value(_nameHist{0}.value)
    -> Junction_29

Bookmark: Track
UniqueIdentifierGenerator_6
    UUID_ATTR = UUID_Track
    UUID_FORMAT = UUID_ONLY
    -> StringConcatenator_7
StringConcatenator_7
    ACTION = Create New Attribute
    PARM_LINE = fme_basicstring:9%18:Track_id_@Value(UUID_Track)
    VAL_ATTR = _result
    -> AttributeManager_11
AttributeManager_11
    ATTR_TABLE:
      SET_TO gml_parent_id (varchar(43)) = STHLM
      SET_TO citygml_feature_role (varchar(16)) = CityObjectMember
      SET_TO gml_id (varchar(7)) = @Value(_result)
    -> AttributeCreator_19
AttributeCreator_19
    ATTR_TABLE:
      SET_TO trecim_intersection_of_track{0}.xlink_href (varchar(200))
      SET_TO trecim_section_of_track{0}.xlink_href (varchar(200))
    -> NullAttributeMapper_8
NullAttributeMapper_8
    ATTRCHOICE_ACTION = ALL
    NULL_TREATMENT_LU = DELETEATTR
    SOURCE_ATTR_VAL_LU = SETNULL EMPTY
    ATTRCHOICE = All Attributes
    NULL_TREATMENT = Missing
    SOURCE_ATTR_VAL = Null Empty
    -> AttributeRemover_8
AttributeRemover_8
    LIST_ATTRS = _list{} _list{}.ROUTE_ID _list{}.de9im _list{}.pass{}
    REMOVE_ATTRS = 4_Track,LOD2,UUID_Intersection,UUID_Section,UUID_Track,_result
    -> GeometryRemover_3
    -> UniqueIdentifierGenerator_13
    -> Junction_9
GeometryRemover_3
    REMOVE_COORDSYS = No
    -> Track (writer CITYGML_1)
UniqueIdentifierGenerator_13 [off]
    UUID_ATTR = UUID_Track
    UUID_FORMAT = UUID_ONLY
    -> StringConcatenator_13
StringConcatenator_13
    ACTION = Create New Attribute
    PARM_LINE = fme_basicstring:11%18:LOD1_Track_@Value(UUID_Track)
    VAL_ATTR = _result
    -> AttributeManager_23
AttributeManager_23
    ATTR_TABLE:
      SET_TO gml_id (varchar(7)) = @Value(_result)
      SET_TO citygml_lod_name (varchar(200))
      SET_TO = lod1MultiSurface
    -> AttributeRemover_20
AttributeRemover_20
    REMOVE_ATTRS = 4_Track,UUID_Section,_predicate,_result
    -> Track (writer CITYGML_1)
Track (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.informationSystem xml_xml, citygml_generalizes_to{}.xlink_href xml_buffer, citygml_relative_to_terrain xml_char(33), citygml_relative_to_water xml_char(38), trecim_absolut_lagesosakerhet_hojd{} xml_real64, trecim_absolut_lagesosakerhet_plan{} xml_real64, trecim_co_class{}.trecim_co_class_trecim_co_class_id xml_buffer, trecim_co_class{}.trecim_co_class_trecim_co_class_kod{} xml_buffer, trecim_co_class{}.trecim_co_class_trecim_co_class_version xml_buffer, trecim_metod_ihojd_tidsperiod_fran{} xml_datetime, trecim_metod_ihojd_tidsperiod_till{} xml_datetime, trecim_metod_ihojd_typ{} xml_buffer, trecim_metod_ihojd_typ{}.codeSpace xml_buffer, trecim_metod_iplan_tidsperiod_fran{} xml_datetime, trecim_metod_iplan_tidsperiod_till{} xml_datetime, trecim_metod_iplan_typ{} xml_buffer, trecim_metod_iplan_typ{}.codeSpace xml_buffer, trecim_objekt_uuid{} xml_buffer, trecim_osakert_lage{} xml_buffer, trecim_osakert_lage{}.codeSpace xml_buffer, trecim_status{} xml_buffer,
      trecim_status{}.codeSpace xml_buffer, trecim_tidpunkt_for_kontroll_av_geometri{} xml_datetime, trecim_tidpunkt_for_lagesbestamning{} xml_datetime, trecim_valid_from{} xml_datetime, trecim_valid_to{} xml_datetime, trecim_version{} xml_int64, citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, trecim_intersection_of_track{}.xlink_href xml_buffer, trecim_section_of_track{}.xlink_href xml_buffer
Note: AttributeRemover_10 : Input
Junction_9
    -> Junction_10

Bookmark: CityModel
Sampler
    MODE = ORIGINAL
    RATE = 1
    SAMPLE_TYPE_MULTIPLIER = -1
    SAMPLE_MODE = No
    SAMPLE_TYPE_LONG = First N Features
    SAMPLED -> AttributeManager_19
AttributeManager_19
    -> UniqueIdentifierGenerator_4
UniqueIdentifierGenerator_4
    UUID_ATTR = UUID_Cit
    UUID_FORMAT = UUID_ONLY
    -> StringConcatenator_6
StringConcatenator_6
    ACTION = Create New Attribute
    PARM_LINE = fme_basicstring:7%16:City_d_@Value(UUID_Cit)
    VAL_ATTR = _result
    -> AttributeManager_20
AttributeManager_20
    ATTR_TABLE:
      SET_TO gml_id (varchar(7)) = STHLM
      SET_TO gml_name (varchar(3000)) = STHLM
    -> AttributeKeeper
AttributeKeeper
    CREATE_BULK_MODE_FEATURES = NO
    KEEP_ATTRS = gml_id,gml_name
    -> GeometryRemover_7
GeometryRemover_7
    REMOVE_COORDSYS = No
    -> CityModel (writer CITYGML_1)
CityModel (writer CITYGML_1)
    attributes: gml_name xml_char(3000)

Bookmark: Road
UniqueIdentifierGenerator_11
    UUID_ATTR = UUID_Road
    UUID_FORMAT = UUID_ONLY
    -> StringConcatenator_10
StringConcatenator_10
    ACTION = Create New Attribute
    PARM_LINE = fme_basicstring:8%17:Road_id_@Value(UUID_Road)
    VAL_ATTR = _result
    -> AttributeManager_13
AttributeManager_13
    ATTR_TABLE:
      SET_TO gml_parent_id (varchar(43)) = STHLM
      SET_TO citygml_feature_role (varchar(16)) = CityObjectMember
      SET_TO gml_id (varchar(7)) = @Value(_result)
    -> NullAttributeMapper_12
NullAttributeMapper_12
    ATTRCHOICE_ACTION = ALL
    NULL_TREATMENT_LU = DELETEATTR
    SOURCE_ATTR_VAL_LU = SETNULL EMPTY
    ATTRCHOICE = All Attributes
    NULL_TREATMENT = Missing
    SOURCE_ATTR_VAL = Null Empty
    -> AttributeRemover_19
AttributeRemover_19
    LIST_ATTRS = _list{} _list{}.ROUTE_ID _list{}.de9im _list{}.pass{}
    REMOVE_ATTRS = 4_Track,LOD2,UUID_Intersection,UUID_Section,_result,UUID_Road
    -> GeometryRemover_6
    -> UniqueIdentifierGenerator_12
    -> Junction_15
GeometryRemover_6
    REMOVE_COORDSYS = No
    -> Road (writer CITYGML_1)
UniqueIdentifierGenerator_12 [off]
    UUID_ATTR = UUID_Road
    UUID_FORMAT = UUID_ONLY
    -> StringConcatenator_11
StringConcatenator_11
    ACTION = Create New Attribute
    PARM_LINE = fme_basicstring:10%17:LOD1_Road_@Value(UUID_Road)
    VAL_ATTR = _result
    -> AttributeManager_22
AttributeManager_22
    ATTR_TABLE:
      SET_TO gml_id (varchar(7)) = @Value(_result)
      SET_TO citygml_lod_name (varchar(16)) = lod1MultiSurface
    -> AttributeRemover_18
AttributeRemover_18
    REMOVE_ATTRS = 4_Track,UUID_Section,_predicate,_result
    -> Road (writer CITYGML_1)
Road (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.informationSystem xml_xml, citygml_generalizes_to{}.xlink_href xml_buffer, citygml_relative_to_terrain xml_char(33), citygml_relative_to_water xml_char(38), trecim_absolut_lagesosakerhet_hojd{} xml_real64, trecim_absolut_lagesosakerhet_plan{} xml_real64, trecim_co_class{}.trecim_co_class_trecim_co_class_id xml_buffer, trecim_co_class{}.trecim_co_class_trecim_co_class_kod{} xml_buffer, trecim_co_class{}.trecim_co_class_trecim_co_class_version xml_buffer, trecim_metod_ihojd_tidsperiod_fran{} xml_datetime, trecim_metod_ihojd_tidsperiod_till{} xml_datetime, trecim_metod_ihojd_typ{} xml_buffer, trecim_metod_ihojd_typ{}.codeSpace xml_buffer, trecim_metod_iplan_tidsperiod_fran{} xml_datetime, trecim_metod_iplan_tidsperiod_till{} xml_datetime, trecim_metod_iplan_typ{} xml_buffer, trecim_metod_iplan_typ{}.codeSpace xml_buffer, trecim_objekt_uuid{} xml_buffer, trecim_osakert_lage{} xml_buffer, trecim_osakert_lage{}.codeSpace xml_buffer, trecim_status{} xml_buffer,
      trecim_status{}.codeSpace xml_buffer, trecim_tidpunkt_for_kontroll_av_geometri{} xml_datetime, trecim_tidpunkt_for_lagesbestamning{} xml_datetime, trecim_valid_from{} xml_datetime, trecim_valid_to{} xml_datetime, trecim_version{} xml_int64, citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, trecim_intersection_of_road{}.xlink_href xml_buffer, trecim_section_of_road{}.xlink_href xml_buffer
Note: AttributeRemover_10 : Input
Junction_15
    -> Junction_19

Bookmark: Intersection
AttributeManager
    ATTR_TABLE:
      SET_TO citygml_feature_role (varchar(18)) = intersectionOfRoad
      SET_TO gml_id (varchar(7)) = @Value(gml_parent_id)
    -> NullAttributeMapper_3
NullAttributeMapper_3
    ATTRCHOICE_ACTION = ALL
    NULL_TREATMENT_LU = DELETEATTR
    SOURCE_ATTR_VAL_LU = SETNULL EMPTY
    ATTRCHOICE = All Attributes
    NULL_TREATMENT = Missing
    SOURCE_ATTR_VAL = Null Empty
    -> SpatialFilter_3 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_10
AttributeManager_10
    ATTR_TABLE = SET_TO gml_parent_id (varchar(200)) = @Value(help_id)
    -> AttributeRemover_9
AttributeRemover_9
    LIST_ATTRS = _list{} _list{}.ROUTE_ID _list{}.de9im _list{}.pass{}
    REMOVE_ATTRS = LOD2,UUID_Intersection,UUID_Section,help_id
    -> GeometryRemover_2
GeometryRemover_2
    REMOVE_COORDSYS = No
    -> Intersection (writer CITYGML_1)
Intersection (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.informationSystem xml_xml, citygml_generalizes_to{}.xlink_href xml_buffer, citygml_relative_to_terrain xml_char(33), citygml_relative_to_water xml_char(38), trecim_absolut_lagesosakerhet_hojd{} xml_real64, trecim_absolut_lagesosakerhet_plan{} xml_real64, trecim_co_class{}.trecim_co_class_trecim_co_class_id xml_buffer, trecim_co_class{}.trecim_co_class_trecim_co_class_kod{} xml_buffer, trecim_co_class{}.trecim_co_class_trecim_co_class_version xml_buffer, trecim_metod_ihojd_tidsperiod_fran{} xml_datetime, trecim_metod_ihojd_tidsperiod_till{} xml_datetime, trecim_metod_ihojd_typ{} xml_buffer, trecim_metod_ihojd_typ{}.codeSpace xml_buffer, trecim_metod_iplan_tidsperiod_fran{} xml_datetime, trecim_metod_iplan_tidsperiod_till{} xml_datetime, trecim_metod_iplan_typ{} xml_buffer, trecim_metod_iplan_typ{}.codeSpace xml_buffer, trecim_objekt_uuid{} xml_buffer, trecim_osakert_lage{} xml_buffer, trecim_osakert_lage{}.codeSpace xml_buffer, trecim_status{} xml_buffer,
      trecim_status{}.codeSpace xml_buffer, trecim_tidpunkt_for_kontroll_av_geometri{} xml_datetime, trecim_tidpunkt_for_lagesbestamning{} xml_datetime, trecim_valid_from{} xml_datetime, trecim_valid_to{} xml_datetime, trecim_version{} xml_int64, citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, trecim_intersection_of_road{}.xlink_href xml_buffer, trecim_section_of_road{}.xlink_href xml_buffer

Bookmark: Section
Tester_3
    BOOL_OP = OR
    TEST_CLAUSE = TEST 4_Track ATTRIBUTE_HAS_A_VALUE ""
    TEST_MODE = TEST
    PASSED -> AttributeManager_2
    FAILED -> Tester_4
AttributeManager_2
    ATTR_TABLE:
      SET_TO citygml_feature_role (varchar(14)) = sectionOfTrack
      SET_TO gml_id (varchar(7)) = @Value(gml_parent_id)
    -> NullAttributeMapper_4
Tester_4
    BOOL_OP = OR
    TEST_CLAUSE = TEST @Value(citygml_function{0}) = 10500
    TEST_MODE = TEST
    PASSED -> AttributeManager_8
    FAILED -> AttributeManager_9
AttributeManager_8
    ATTR_TABLE:
      SET_TO citygml_feature_role (varchar(15)) = sectionOfSquare
      SET_TO gml_id (varchar(7)) = @Value(gml_parent_id)
    -> NullAttributeMapper_4
AttributeManager_9
    ATTR_TABLE:
      SET_TO citygml_feature_role (varchar(15)) = sectionOfRoad
      SET_TO gml_id (varchar(7)) = @Value(gml_parent_id)
      SET_TO
    -> NullAttributeMapper_4
NullAttributeMapper_4
    ATTRCHOICE_ACTION = ALL
    NULL_TREATMENT_LU = DELETEATTR
    SOURCE_ATTR_VAL_LU = SETNULL EMPTY
    ATTRCHOICE = All Attributes
    NULL_TREATMENT = Missing
    SOURCE_ATTR_VAL = Null Empty
    -> SpatialFilter_7 [Candidate]
SpatialFilter_7
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_18
AttributeManager_18
    ATTR_TABLE = SET_TO gml_parent_id (varchar(200)) = @Value(help_id)
    -> AttributeRemover_7
AttributeRemover_7
    LIST_ATTRS = _list{} _list{}.ROUTE_ID _list{}.de9im _list{}.pass{}
    REMOVE_ATTRS = LOD2,UUID_Intersection,UUID_Section,help_id
    -> DuplicateFilter
DuplicateFilter
    INPUT_ORDERED_CHOICE_LOOKUP = NO
    KEYATTR = gml_id
    INPUT_ORDERED_CHOICE = No
    UNIQUE -> Junction_26
    DUPLICATE -> Counter
Counter
    CNT_ATTR = _count
    DOMAIN = counter
    SCOPE = Global
    START = 0
    -> StringConcatenator_12
StringConcatenator_12
    ACTION = Create New Attribute
    PARM_LINE = fme_basicstring:14%14:@Value(gml_id)@Value(_count)
    VAL_ATTR = _result
    -> Junction_26
Junction_26
    -> GeometryRemover_4
GeometryRemover_4
    REMOVE_COORDSYS = No
    -> Section (writer CITYGML_1)
Section (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.informationSystem xml_xml, citygml_generalizes_to{}.xlink_href xml_buffer, citygml_relative_to_terrain xml_char(33), citygml_relative_to_water xml_char(38), trecim_absolut_lagesosakerhet_hojd{} xml_real64, trecim_absolut_lagesosakerhet_plan{} xml_real64, trecim_co_class{}.trecim_co_class_trecim_co_class_id xml_buffer, trecim_co_class{}.trecim_co_class_trecim_co_class_kod{} xml_buffer, trecim_co_class{}.trecim_co_class_trecim_co_class_version xml_buffer, trecim_metod_ihojd_tidsperiod_fran{} xml_datetime, trecim_metod_ihojd_tidsperiod_till{} xml_datetime, trecim_metod_ihojd_typ{} xml_buffer, trecim_metod_ihojd_typ{}.codeSpace xml_buffer, trecim_metod_iplan_tidsperiod_fran{} xml_datetime, trecim_metod_iplan_tidsperiod_till{} xml_datetime, trecim_metod_iplan_typ{} xml_buffer, trecim_metod_iplan_typ{}.codeSpace xml_buffer, trecim_objekt_uuid{} xml_buffer, trecim_osakert_lage{} xml_buffer, trecim_osakert_lage{}.codeSpace xml_buffer, trecim_status{} xml_buffer,
      trecim_status{}.codeSpace xml_buffer, trecim_tidpunkt_for_kontroll_av_geometri{} xml_datetime, trecim_tidpunkt_for_lagesbestamning{} xml_datetime, trecim_valid_from{} xml_datetime, trecim_valid_to{} xml_datetime, trecim_version{} xml_int64, citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer, trecim_intersection_of_road{}.xlink_href xml_buffer, trecim_section_of_road{}.xlink_href xml_buffer

Bookmark: Auxiliary
AttributeRemover_21
    REMOVE_ATTRS = 1_Temaklass,2_Klass,3_Subklass,4_Slask,4_Track,BM_ANVD,CTYPE_NAME,DP_OID,GCM_t_502,Intersection,LOD1,LOD2,LOD3,MARK_TEXT,Not_Road,Section,Typ_512,Utfyllnad,Vagtr_474,_length,_overlaps,fme_fill_color,sub_c_type,UUID_Intersection,UUID_Section,_concatenated,_related_suppliers
    -> AttributeCreator_20
AttributeCreator_20
    ATTR_TABLE:
      SET_TO trecim_marking{0}.xlink_href (varchar(200))
      SET_TO citygml_level_of_detail{0} (varchar(5)) = 2
    -> AttributeRemover_4
AttributeRemover_4
    LIST_ATTRS = _list{} _list{}.ROUTE_ID _list{}.de9im _list{}.pass{}
    REMOVE_ATTRS = 4_Track,LOD2,UUID_Intersection,UUID_Section,_list{0}.ROUTE_ID,_list{0}.de9im,_list{0}.pass{0}
    -> NullAttributeMapper_2
NullAttributeMapper_2
    ATTRCHOICE_ACTION = ALL
    NULL_TREATMENT_LU = DELETEATTR
    SOURCE_ATTR_VAL_LU = SETNULL EMPTY
    ATTRCHOICE = All Attributes
    NULL_TREATMENT = Missing
    SOURCE_ATTR_VAL = Null Empty
    -> CityGMLGeometrySetter_3
CityGMLGeometrySetter_3
    GEOM = lod2MultiSurface
    ROLE = auxiliaryTrafficArea
    -> AuxiliaryTrafficArea (writer CITYGML_1)
AuxiliaryTrafficArea (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.informationSystem xml_xml, citygml_generalizes_to{}.xlink_href xml_buffer, citygml_relative_to_terrain xml_char(33), citygml_relative_to_water xml_char(38), trecim_absolut_lagesosakerhet_hojd{} xml_real64, trecim_absolut_lagesosakerhet_plan{} xml_real64, trecim_co_class{}.trecim_co_class_trecim_co_class_id xml_buffer, trecim_co_class{}.trecim_co_class_trecim_co_class_kod{} xml_buffer, trecim_co_class{}.trecim_co_class_trecim_co_class_version xml_buffer, trecim_metod_ihojd_tidsperiod_fran{} xml_datetime, trecim_metod_ihojd_tidsperiod_till{} xml_datetime, trecim_metod_ihojd_typ{} xml_buffer, trecim_metod_ihojd_typ{}.codeSpace xml_buffer, trecim_metod_iplan_tidsperiod_fran{} xml_datetime, trecim_metod_iplan_tidsperiod_till{} xml_datetime, trecim_metod_iplan_typ{} xml_buffer, trecim_metod_iplan_typ{}.codeSpace xml_buffer, trecim_objekt_uuid{} xml_buffer, trecim_osakert_lage{} xml_buffer, trecim_osakert_lage{}.codeSpace xml_buffer, trecim_status{} xml_buffer,
      trecim_status{}.codeSpace xml_buffer, trecim_tidpunkt_for_kontroll_av_geometri{} xml_datetime, trecim_tidpunkt_for_lagesbestamning{} xml_datetime, trecim_valid_from{} xml_datetime, trecim_valid_to{} xml_datetime, trecim_version{} xml_int64, citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer

Bookmark: TrafficArea
AttributeCreator_7
    ATTR_TABLE:
      SET_TO trecim_marking{0}.xlink_href (varchar(200))
      SET_TO citygml_level_of_detail{0} (varchar(5)) = 2
    -> AttributeRemover_3
AttributeRemover_3
    LIST_ATTRS = _list{} _list{}.ROUTE_ID _list{}.de9im _list{}.pass{}
    REMOVE_ATTRS = 4_Track,LOD2,UUID_Intersection,UUID_Section,_list{0}.ROUTE_ID,_list{0}.de9im,_list{0}.pass{0}
    -> NullAttributeMapper_5
NullAttributeMapper_5
    ATTRCHOICE_ACTION = ALL
    NULL_TREATMENT_LU = DELETEATTR
    SOURCE_ATTR_VAL_LU = SETNULL EMPTY
    ATTRCHOICE = All Attributes
    NULL_TREATMENT = Missing
    SOURCE_ATTR_VAL = Null Empty
    -> CityGMLGeometrySetter_2
CityGMLGeometrySetter_2
    GEOM = lod2MultiSurface
    ROLE = trafficArea
    -> TrafficArea (writer CITYGML_1)
TrafficArea (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.informationSystem xml_xml, citygml_generalizes_to{}.xlink_href xml_buffer, citygml_relative_to_terrain xml_char(33), citygml_relative_to_water xml_char(38), trecim_absolut_lagesosakerhet_hojd{} xml_real64, trecim_absolut_lagesosakerhet_plan{} xml_real64, trecim_co_class{}.trecim_co_class_trecim_co_class_id xml_buffer, trecim_co_class{}.trecim_co_class_trecim_co_class_kod{} xml_buffer, trecim_co_class{}.trecim_co_class_trecim_co_class_version xml_buffer, trecim_metod_ihojd_tidsperiod_fran{} xml_datetime, trecim_metod_ihojd_tidsperiod_till{} xml_datetime, trecim_metod_ihojd_typ{} xml_buffer, trecim_metod_ihojd_typ{}.codeSpace xml_buffer, trecim_metod_iplan_tidsperiod_fran{} xml_datetime, trecim_metod_iplan_tidsperiod_till{} xml_datetime, trecim_metod_iplan_typ{} xml_buffer, trecim_metod_iplan_typ{}.codeSpace xml_buffer, trecim_objekt_uuid{} xml_buffer, trecim_osakert_lage{} xml_buffer, trecim_osakert_lage{}.codeSpace xml_buffer, trecim_status{} xml_buffer,
      trecim_status{}.codeSpace xml_buffer, trecim_tidpunkt_for_kontroll_av_geometri{} xml_datetime, trecim_tidpunkt_for_lagesbestamning{} xml_datetime, trecim_valid_from{} xml_datetime, trecim_valid_to{} xml_datetime, trecim_version{} xml_int64, citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_surface_material xml_buffer, citygml_surface_material_codeSpace xml_buffer, citygml_level_of_detail{} xml_buffer, trecim_marking{}.xlink_href xml_buffer

Bookmark: Square
UniqueIdentifierGenerator_9 [off]
    UUID_ATTR = UUID_Square
    UUID_FORMAT = UUID_ONLY
    -> StringConcatenator_9
StringConcatenator_9 [off]
    ACTION = Create New Attribute
    PARM_LINE = fme_basicstring:10%19:Square_id_@Value(UUID_Square)
    VAL_ATTR = _result
    -> AttributeManager_12
AttributeManager_12
    ATTR_TABLE:
      SET_TO gml_id (varchar(7)) = @Value(gml_parent_id)
      SET_TO gml_parent_id (varchar(43)) = STHLM
      SET_TO citygml_feature_role (varchar(16)) = CityObjectMember
    -> NullAttributeMapper_11
NullAttributeMapper_11
    ATTRCHOICE_ACTION = ALL
    NULL_TREATMENT_LU = DELETEATTR
    SOURCE_ATTR_VAL_LU = SETNULL EMPTY
    ATTRCHOICE = All Attributes
    NULL_TREATMENT = Missing
    SOURCE_ATTR_VAL = Null Empty
    -> AttributeRemover_17
AttributeRemover_17
    LIST_ATTRS = _list{} _list{}.ROUTE_ID _list{}.de9im _list{}.pass{}
    REMOVE_ATTRS = 4_Track,LOD2,UUID_Intersection,UUID_Section,_result,UUID_Square,_list{0}.ROUTE_ID,_list{0}.de9im,_list{0}.pass{0}
    -> GeometryRemover_5
    -> UniqueIdentifierGenerator_5
    -> Junction_12
GeometryRemover_5
    REMOVE_COORDSYS = No
    -> Square (writer CITYGML_1)
UniqueIdentifierGenerator_5 [off]
    UUID_ATTR = UUID_Square
    UUID_FORMAT = UUID_ONLY
    -> StringConcatenator_8
StringConcatenator_8
    ACTION = Create New Attribute
    PARM_LINE = fme_basicstring:12%19:LOD1_Square_@Value(UUID_Square)
    VAL_ATTR = _result
    -> AttributeManager_21
AttributeManager_21
    ATTR_TABLE:
      SET_TO gml_id (varchar(7)) = @Value(_result)
      SET_TO citygml_lod_name (varchar(16)) = lod1MultiSurface
    -> AttributeRemover_13
AttributeRemover_13
    REMOVE_ATTRS = 4_Track,UUID_Section,_predicate,_result
    -> Square (writer CITYGML_1)
Square (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.informationSystem xml_xml, citygml_generalizes_to{}.xlink_href xml_buffer, citygml_relative_to_terrain xml_char(33), citygml_relative_to_water xml_char(38), trecim_absolut_lagesosakerhet_hojd{} xml_real64, trecim_absolut_lagesosakerhet_plan{} xml_real64, trecim_co_class{}.trecim_co_class_trecim_co_class_id xml_buffer, trecim_co_class{}.trecim_co_class_trecim_co_class_kod{} xml_buffer, trecim_co_class{}.trecim_co_class_trecim_co_class_version xml_buffer, trecim_metod_ihojd_tidsperiod_fran{} xml_datetime, trecim_metod_ihojd_tidsperiod_till{} xml_datetime, trecim_metod_ihojd_typ{} xml_buffer, trecim_metod_ihojd_typ{}.codeSpace xml_buffer, trecim_metod_iplan_tidsperiod_fran{} xml_datetime, trecim_metod_iplan_tidsperiod_till{} xml_datetime, trecim_metod_iplan_typ{} xml_buffer, trecim_metod_iplan_typ{}.codeSpace xml_buffer, trecim_objekt_uuid{} xml_buffer, trecim_osakert_lage{} xml_buffer, trecim_osakert_lage{}.codeSpace xml_buffer, trecim_status{} xml_buffer,
      trecim_status{}.codeSpace xml_buffer, trecim_tidpunkt_for_kontroll_av_geometri{} xml_datetime, trecim_tidpunkt_for_lagesbestamning{} xml_datetime, trecim_valid_from{} xml_datetime, trecim_valid_to{} xml_datetime, trecim_version{} xml_int64, citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_traffic_area{}.xlink_href xml_buffer, citygml_auxiliary_traffic_area{}.xlink_href xml_buffer, citygml_level_of_detail{} xml_buffer
Note: AttributeRemover_10 : Input
Junction_12 [off]
    -> Junction_14 [off]
